FME workspace FKB_Vegnett.fmw

Parameters:
- DEF_VAL = 403;502;520   # " " Kommuner
- gmlFolder = C:\DATA\GitHub\NVDBGML\GML   # Hovedmappe
- xsdName = fkbvn   # skjemanavn
- gmlNs = https://raw.githubusercontent.com/jetgeo/NVDBGML/master/XSD/NVDB   # GML Namespace
- omr = kommune   # Områdetype

Creator
    GEOMTYPE = Geometry Object
    NUM = 1
    CREATED -> AttributeManager
AttributeManager
    ATTR_TABLE = SET_TO kommuner = $(DEF_VAL)
    -> AttributeSplitter
AttributeSplitter
    ATTR_NAME = kommuner
    DELIMITER = ;
    DROP_EMPTY_PARTS = No
    LIST_NAME = _kommune
    TRIM_OPTION = Both
    -> ListExploder_2
ListExploder_2
    ATTR_ACCUM_MODE = Merge List Attributes
    ATTR_CONFLICT_RES = Use List Attribute Values
    INDEX_ATTR = _element_index
    LIST_ATTR = _kommune{}
    ELEMENTS -> WorkspaceRunner
WorkspaceRunner
    BLOCKING = Yes
    WORKSPACE_FILE = $(FME_MF_DIR)NVDBAPI2GML_V2_Vegnett_2018.fmw
    WORKSPACE_PARAMETERS = omr,kommune,omrNvn,@Value(_kommune),gmlFolder,$(gmlFolder)
    SUCCEEDED -> WorkspaceRunner_2
WorkspaceRunner_2
    BLOCKING = Yes
    WORKSPACE_FILE = $(FME_MF_DIR)gml2gdmmappersosi.fmw
    WORKSPACE_PARAMETERS = kommune,@Value(_kommune),mainFolder,$(gmlFolder)
    SUCCEEDED -> WorkspaceRunner_2_Succeeded
    FAILED -> WorkspaceRunner_2_Failed
    SUMMARY -> WorkspaceRunner_2_Summary
WorkspaceRunner_2_Succeeded: Inspector
WorkspaceRunner_2_Failed: Inspector
WorkspaceRunner_2_Summary: Inspector
