FME workspace NVDBAPI2GML_V2_Vegnett_2018.fmw

Parameters:
- omr = kommune   # Områdetype
- omrNvn = 403   # Område
- gmlFolder = C:\DATA\GitHub\SOSI-Vegnett\GML   # GML-hovedmappe
- xsdName = fkbvn   # skjemanavn
- gmlNs = https://raw.githubusercontent.com/jetgeo/NVDBGML/master/XSD/NVDB   # GML Namespace
- fullGmlNs:   # Python Script
      ns = FME_MacroValues['gmlNs'] + '/' + FME_MacroValues['xsdName']
      return ns
- xsd:   # Python Script
      xsd = FME_MacroValues['fullGmlNs'] + '/' + FME_MacroValues['xsdName'] + '.xsd'
      return xsd
- sl:   # Python Script
      sl = FME_MacroValues['fullGmlNs'] + ' ' + FME_MacroValues['fullGmlNs'] + '/' + FME_MacroValues['xsdName'] + '.xsd'
      return sl
- fullGmlFolder:   # Python Script
      fldr = FME_MacroValues['gmlFolder'] + '\\' + FME_MacroValues['omr'] + '\\' + FME_MacroValues['omrNvn'] + '\\' + FME_MacroValues['xsdName']
      return fldr

Writers:
- GML_1: GML to $(fullGmlFolder)

Creator
    GEOMTYPE = Geometry Object
    NUM = 1
    CREATED -> AttributeCreator
AttributeCreator
    ATTR_TABLE:
      SET_TO href = https://utv.vegvesen.no/nvdb/api/v2/vegnett/lenker?$(omr)=$(omrNvn)&antall=5000

      SET_TO omrNvn = $(omrNvn)
      SET_TO omr = $(omr)
    -> NVDB_Vegnettleser [_Input]
AttributeManager_6
    ATTR_TABLE:
      SET_TO lenkesekvensid = @Value(veglenkeid)
      SET_TO fraPosisjon = @Value(lenkesekvens.Lenkesekvensreferanse.startposisjon)
      SET_TO tilPosisjon = @Value(lenkesekvens.Lenkesekvensreferanse.sluttposisjon)
      SET_TO orgLenkeFraPos = @Value(lenkesekvens.Lenkesekvensreferanse.startposisjon)
      SET_TO orgLenkeTilPos = @Value(lenkesekvens.Lenkesekvensreferanse.sluttposisjon)
    -> StringFormatter_3
StringFormatter_3
    FORMAT = .8f
    SRC_ATTRS = orgLenkeFraPos,orgLenkeTilPos
    -> EventOverlayer_2 [Event_table_A]
    -> EventGeometry [Network]
Creator_3
    GEOMTYPE = Geometry Object
    NUM = 1
    CREATED -> AttributeManager_2
    CREATED -> AttributeManager_13
AttributeManager_13 [off]
    ATTR_TABLE = SET_TO ftIDs = 105
    -> AttributeSplitter
AttributeManager_2
    ATTR_TABLE = SET_TO ftIDs = 538;532;821;105;813;591;606;100;822;573;856;607;107
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> AttributeCreator_2
AttributeCreator_2
    ATTR_TABLE = SET_TO href = https://www.vegvesen.no/nvdb/api/v2/vegobjekter/@Value(_ftID)?$(omr)=$(omrNvn)&antall=5000&inkluder=alle
    -> NVDB_Leser [_Input]
FeatureTypeFilter_2
    ATTRIBUTES = Gate,Vegreferanse,Fartsgrense,FunksjonellVegklasse,Trafikkreguleringer,InnkjøringForbudt,Landbruksvegklasse,VærutsattVeg,Jernbanekryssing,Høydebegrensning,Vegsperring,Gågate,Svingerestriksjon,<Unfiltered>,<Blank>
    Gate -> ListExploder
    Vegreferanse -> ListExploder
    Fartsgrense -> FeatureTypeFilter_2_Fartsgrense_-__AttributeExposer
    FunksjonellVegklasse -> FeatureTypeFilter_2_Fartsgrense_-__AttributeExposer
    Trafikkreguleringer -> FeatureTypeFilter_2_Fartsgrense_-__AttributeExposer
    InnkjøringForbudt -> FeatureTypeFilter_2_Fartsgrense_-__AttributeExposer
    Landbruksvegklasse -> FeatureTypeFilter_2_Fartsgrense_-__AttributeExposer
    VærutsattVeg -> FeatureTypeFilter_2_Fartsgrense_-__AttributeExposer
    Jernbanekryssing -> FeatureTypeFilter_2_Fartsgrense_-__AttributeExposer
    Høydebegrensning -> FeatureTypeFilter_2_Fartsgrense_-__AttributeExposer
    Vegsperring -> FeatureTypeFilter_2_Fartsgrense_-__AttributeExposer
    Gågate -> AttributeManager
    Svingerestriksjon -> ListIndexer_3
ListExploder
    ATTR_ACCUM_MODE = Merge List Attributes
    ATTR_CONFLICT_RES = Use List Attribute Values
    INDEX_ATTR = _element_index
    LIST_ATTR = lineærPosisjon{}
    ELEMENTS -> AttributeManager_3
AttributeManager_3
    ATTR_TABLE:
      SET_TO lenkesekvensid = @Value(LineærPosisjonStrekning.veglenkeid)
      SET_TO fraPosisjon = @Value(LineærPosisjonStrekning.fraPosisjon)
      SET_TO tilPosisjon = @Value(LineærPosisjonStrekning.tilPosisjon)
    -> FeatureTypeFilter_3
FeatureTypeFilter_3
    ATTRIBUTES = Vegreferanse,Gate,<Unfiltered>,<Blank>
    Vegreferanse -> AttributeExposer_2
    Gate -> AttributeExposer_3
Note: Segmenterer mot vegreferanse
EventOverlayer_2
    FromVal = @Value(fraPosisjon)
    RoadLinkID = @Value(lenkesekvensid)
    ToVal = @Value(tilPosisjon)
    Common_Segments -> AttributeManager_8
    Only_A -> AttributeManager_8
    Only_B -> AttributeManager_8
AttributeManager_8
    ATTR_TABLE:
      RENAME_SET_VALUE FromVal > fraPosisjon
      RENAME_SET_VALUE ToVal > tilPosisjon
      REMOVE _SegId
    -> EventOverlayer [Event_table_A]
Note: Segmenterer mot Gate
EventOverlayer
    FromVal = @Value(fraPosisjon)
    RoadLinkID = @Value(lenkesekvensid)
    ToVal = @Value(tilPosisjon)
    Common_Segments -> AttributeManager_7
    Only_A -> AttributeManager_7
    Only_B -> AttributeManager_7
AttributeManager_7
    ATTR_TABLE:
      RENAME_SET_VALUE FromVal > fraPosisjon
      RENAME_SET_VALUE ToVal > tilPosisjon
      REMOVE _SegId
    -> EventGeometry [Events]
Note: Kobler geometri til segmentene
EventGeometry
    _dimension = 2
    _eventFrom = @Value(fraPosisjon)
    _eventRouteID = @Value(lenkesekvensid)
    _eventTo = @Value(tilPosisjon)
    _measureMode = 2D
    _rlFrom = @Value(fraPosisjon)
    _rlRouteID = @Value(lenkesekvensid)
    _rlTo = @Value(tilPosisjon)
    Lines -> StringFormatter_2
Note: Avrunder til 8 desimaler for å unngå / problem med eksponentialverdier
StringFormatter_2
    FORMAT = .8f
    SRC_ATTRS = _eventFrom,_eventTo
    -> AttributeManager_5
AttributeManager_5
    ATTR_TABLE:
      REMOVE fraPosisjon
      REMOVE tilPosisjon
      REMOVE _routeID
      RENAME_SET_VALUE _eventID
      RENAME_SET_VALUE _eventFrom > startposisjon
      RENAME_SET_VALUE _eventTo > sluttposisjon
      SET_TO vegreferanse.Vegreferanse.referanseretning = med
    -> NullAttributeMapper_2
NullAttributeMapper_2
    ATTRCHOICE = All Attributes
    NULL_TREATMENT = Missing
    SOURCE_ATTR_VAL = Empty Null
    -> GeometryExtractor
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    KIND_LONG = FME Binary
    LETTERING = WGS84
    LEVELS_ATTR = _levels
    MSSQL_FORMAT_CHOICE = Geometry
    OGCVERSION = 1.2
    OGC_WKT_PRECISION_DISPLAY = Shortened 64-bit
    OGEOSMS_URL_PREFIX = http://maps.google.com/?q=
    OMIT_NAMESPACES_DISPLAY = No
    PRECISION = 0
    PREFER_POLYGON_OVER_SURFACE = No
    REMOVE_GEOMETRY = No
    -> Matcher
Matcher
    BLANK_AND_MISSING_DIFFER = No
    CNT_ATTR = _match_id
    LENIENT_MATCH = No
    MATCH = NONE
    MATCHATTRS = lenkesekvensid
    MATCH_STRATEGY = Match Selected Attributes
    SM_LIST_NAME = _duplicates
    SINGLE_MATCHED -> ListExploder_3
    NOT_MATCHED -> AttributeManager_9
Note: Sett lenkesekvens.fraPosisjon og tilPosisjon
AttributeManager_15
    ATTR_TABLE:
      RENAME_SET_VALUE startposisjon > lenkesekvens.Lenkesekvensreferanse.startposisjon
      RENAME_SET_VALUE sluttposisjon > lenkesekvens.Lenkesekvensreferanse.sluttposisjon
    -> AttributeFilter_2
AttributeFilter_2
    ATTR_NAME = detaljnivå
    ATTR_VALUES = <Empty>,<Missing>,<Null>,<Unfiltered>,kjørebane,kjørefelt,vegtrase
    <MISSING> -> GeometryPropertySetter_2
    <MISSING> -> FeatureMerger_2 [SUPPLIER]
    kjørebane -> AttributeManager_17
    kjørefelt -> AttributeManager_17
    vegtrase -> AttributeKeeper_4
    vegtrase -> Junction_3
Note: GeometryPropertySetter_2 : Input
Junction_3
    -> Junction_4
Note: AttributeFilter_2 : vegtrase
Junction_4
    -> GeometryPropertySetter_2
GeometryPropertySetter_2
    GEOM_NAME_FIELD = senterlinje
    OVERWRITE_CHOICE = Yes
    SETTYPE_PARAM = Geometry Name
    SET -> Vegobjekttype (writer GML_1)
    SET -> Veglenker
Veglenker: Inspector
FeatureTypeFilter_2_Fartsgrense_-__AttributeExposer: Junction
    -> AttributeExposer
AttributeManager
    ATTR_TABLE = SET_TO fme_feature_type = Gågatereguleringer
    -> AttributeExposer
Note: Til GML
Junction
    -> Junction_2
Note: Vegobjekttyper
Junction_2
    -> Vegobjekttype (writer GML_1)
    -> Fagdata
Vegobjekttype (writer GML_1)
    attributes: id xml_char(200), geometri.wkt xml_char(200), xml_fragment xml_char(200), xml_id xml_char(200), xml_matched_element xml_char(200), xml_parent_id xml_char(200), xml_parent_child_pos xml_char(200), identifikasjon.Identifikasjon.lokalId xml_char(200), identifikasjon.Identifikasjon.versjonId xml_char(200), identifikasjon.Identifikasjon.navnerom xml_char(200), assosiasjoner{}.typeId xml_char(200), assosiasjoner{}.vegobjektId xml_char(200), assosiasjoner{}.relasjonstype xml_char(200), epsg xml_char(200), lineærPosisjon{}.LineærPosisjonStrekning.veglenkeid xml_char(200), lineærPosisjon{}.LineærPosisjonStrekning.fraPosisjon xml_char(200), lineærPosisjon{}.LineærPosisjonStrekning.tilPosisjon xml_char(200), _hierarchy_child_id_list{} xml_char(200), _geometry_name xml_char(200), _hierarchy_id xml_char(200), _hierarchy_parent_id xml_char(200), _part_number xml_char(200), _schemamapper_row_ids xml_char(200), kommunenummer xml_char(200), svingeforbudTil.LineærPosisjonStrekning.veglenkeid xml_char(200), svingeforbudTil.LineærPosisjonStrekning.fraPosisjon xml_char(200), svingeforbudTil.LineærPosisjonStrekning.tilPosisjon xml_char(200), svingeforbudFra.LineærPosisjonStrekning.veglenkeid xml_char(200), svingeforbudFra.LineærPosisjonStrekning.fraPosisjon xml_char(200), svingeforbudFra.LineærPosisjonStrekning.tilPosisjon xml_char(200),
      senterlinje xml_char(200), posisjon xml_char(200), lineærPosisjon.LineærPosisjonStrekning.veglenkeid xml_char(200), lineærPosisjon.LineærPosisjonStrekning.fraPosisjon xml_char(200), lineærPosisjon.LineærPosisjonStrekning.tilPosisjon xml_char(200), fme_rejection_code xml_char(200), nettverk{}.xlink_href xml_char(200), _partNr xml_char(200), startnode xml_char(200), sluttnode xml_char(200), veglenkeid xml_char(200), detaljnivå xml_char(200), datafangstdato xml_char(200), medium xml_char(200), kvalitet.Posisjonskvalitet.synbarhet xml_char(200), startnodeId xml_char(200), sluttnodeId xml_char(200), temakode xml_char(200), _element_index xml_char(200), typeVeg xml_char(200), veglenkeadresse.Veglenkeadresse.adressekode xml_char(200), veglenkeadresse.Veglenkeadresse.adressenavn xml_char(200), vegreferanse.Vegreferanse.kommunenummer xml_char(200), lenkesekvensid xml_char(200), RoadLinkID xml_char(200), _length xml_char(200), vegreferanse.Vegreferanse.referanseretning xml_char(200), vegreferanse.Vegreferanse.vegreferanseFraDato xml_char(200), _match_id xml_char(200), _eventID xml_char(200),
      orgLenkeFraPos xml_char(200), orgLenkeTilPos xml_char(200), _geometry xml_char(200), konnekteringslenke xml_char(200), veglenkeadresse.Veglenkeadresse.sideveg xml_char(200), lenkesekvens.Lenkesekvensreferanse.identifikasjon.Identifikasjon.lokalId xml_char(200), lenkesekvens.Lenkesekvensreferanse.startposisjon xml_char(200), lenkesekvens.Lenkesekvensreferanse.sluttposisjon xml_char(200), _fraposisjon.vegreferanse.meter xml_char(200), _tilposisjon.vegreferanse.meter xml_char(200), vegreferanse.Vegreferanse.veglenkeMeterFra xml_char(200), vegreferanse.Vegreferanse.veglenkeMeterTil xml_char(200), foreldrelenkeid xml_char(200), vegreferanse.Vegreferanse.vegkategori xml_char(200), vegreferanse.Vegreferanse.vegnummer xml_char(200), vegreferanse.Vegreferanse.vegstatus xml_char(200), vegreferanse.Vegreferanse.hovedparsell xml_char(200), vegkategori xml_char(200), vegnummer xml_char(200), vegstatus xml_char(200), hovedparsell xml_char(200), veglenkeMeterFra xml_char(200), veglenkeMeterTil xml_char(200)
Fagdata: Inspector
    TACKATTRS = fme_feature_type

Bookmark: Leser og tolker XML fra NVDB-API
Note: Lesing av XML for vegnett:
NVDB_Vegnettleser
    NESTE.HREF = @Value(href)
    OMR = $(omr)
    OMRNVN = $(omrNvn)
    namespace = vegvesen.no.nvdb
    nettverk:
      ns = FME_MacroValues['namespace'] + '.nw.' + FME_MacroValues['OMR'] + '_' + FME_MacroValues['OMRNVN']
      return ns
    Veglenke -> Sampler
    Veglenke -> AttributeManager_6
Sampler [off]
    RATE = 10
    SAMPLE_MODE = No
    SAMPLE_TYPE_LONG = First N Features
    SAMPLED -> AttributeManager_6
Note: Leser fagdata
NVDB_Leser
    NESTE.HREF = @Value(href)
    -> SchemaMapper

Bookmark: Oversetter til GML-verdier og -navn
Note: Oversetter tillatte verdier til GML-verdier
SchemaMapper
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB_enMapping.csv
    FORMAT = CSV2
    IDXDESTATTR = fme_feature_type
    IDXDESTCOL = ""
    IDXSOURCEATTR = fme_feature_type
    IDXSOURCECOL = ""
    MAP_ATTRS = """""" ptid name
    MATCH_ATTRS = ptid enid
    ROW_ID_ATTR = _schemamapper_row_ids
    TABLE = CSV
    MAPPED -> SchemaMapper_2
    UNMAPPED -> SchemaMapper_2
Note: Oversetter egenskapsnavn til GML-navn
SchemaMapper_2
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB_ptMapping.csv
    FORMAT = CSV2
    IDXDESTATTR = fme_feature_type
    IDXDESTCOL = ""
    IDXSOURCEATTR = fme_feature_type
    IDXSOURCECOL = ""
    MAP_ATTRS = ptid name """"""
    MATCH_ATTRS = ft_attr ftid
    ROW_ID_ATTR = _schemamapper_row_ids
    TABLE = CSV
    MAPPED -> NullAttributeMapper_3
    UNMAPPED -> NullAttributeMapper_3
NullAttributeMapper_3
    ATTRCHOICE = All Attributes
    NULL_TREATMENT = Missing
    SOURCE_ATTR_VAL = Empty Null
    -> SchemaMapper_3
Note: Oversetter objekttypenavn til GML-navn
SchemaMapper_3
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB_ftMapping.csv
    FORMAT = CSV2
    IDXDESTATTR = fme_feature_type
    IDXDESTCOL = name
    IDXSOURCEATTR = fme_feature_type
    IDXSOURCECOL = ftid
    ROW_ID_ATTR = _schemamapper_row_ids
    TABLE = CSV
    MAPPED -> FeatureTypeFilter_2

Bookmark: Egenskaper for Vegreferanse
AttributeExposer_2
    ATTR_LIST = vegkategori,vegnummer,hovedparsell,vegstatus,metadata.startdato,fraMeter,tilMeter
    -> AttributeKeeper_2
AttributeKeeper_2
    KEEP_ATTRS = lenkesekvensid,fraPosisjon,metadata.startdato,tilPosisjon
    -> AttributeManager_4
AttributeManager_4
    ATTR_TABLE = RENAME_SET_VALUE metadata.startdato > vegreferanse.Vegreferanse.vegreferanseFraDato
    -> DateFormatter_2
Note: Bruker kun dato fra Vegreferanseobjektet, alt annet ligger allerede på veglenkene fra APIet
DateFormatter_2
    DATE_ATTR = vegreferanse.Vegreferanse.vegreferanseFraDato
    FMT = ISO Date (%Y-%m-%d)
    INVALID_DATE_VALUE = 0001-01-01T00:00:00
    SRCFMT = Unknown - Automatic Detection
    -> EventOverlayer_2 [Event_table_B]

Bookmark: Egenskaper for Gate
AttributeExposer_3
    ATTR_LIST = gatekode,gatenavn,sideveg
    -> AttributeKeeper
AttributeKeeper
    KEEP_ATTRS = gatenavn,fraPosisjon,gatekode,tilPosisjon,sideveg,lenkesekvensid,kommunenummer
    -> AttributeManager_14
AttributeManager_14
    ATTR_TABLE:
      RENAME_SET_VALUE gatekode > veglenkeadresse.Veglenkeadresse.adressekode
      RENAME_SET_VALUE gatenavn > veglenkeadresse.Veglenkeadresse.adressenavn
      REMOVE kommunenummer
      SET_TO veglenkeadresse.Veglenkeadresse.sideveg = FME_CONDITIONAL:DEFAULT_VALUE'_FME_NO_OP_'BOOL_OP;OR;COMPOSITE_TEST;<Unused>;TEST @Value(sideveg) = ja'true'BOOL_OP;OR;COMPOSITE_TEST;<Unused>;TEST @Value(sideveg) = nei'false'FME_NUM_CONDITIONS3___
      REMOVE sideveg
    -> EventOverlayer [Event_table_B]

Bookmark: Lager unik ID for segmentene
ListExploder_3
    ATTR_ACCUM_MODE = Only Use List Attributes
    INDEX_ATTR = _partNr
    LIST_ATTR = _duplicates{}
    ELEMENTS -> GeometryReplacer
GeometryReplacer
    KIND_LONG = FME Binary
    REMOVE_ATTRIBUTE = Yes
    SOURCE = @Value(_geometry)
    -> AttributeManager_9
AttributeManager_9
    ATTR_TABLE:
      SET_TO _partNr = FME_CONDITIONAL:DEFAULT_VALUE'_FME_NO_OP_'BOOL_OP;OR;COMPOSITE_TEST;<Unused>;TEST _partNr ATTRIBUTE_IS_MISSING _FME_BLANK_STRING_'0'FME_NUM_CONDITIONS2___
      SET_TO identifikasjon.Identifikasjon.lokalId = @Value(lenkesekvensid)_@Value(_partNr)
      SET_TO gml_id = vegvesen.no.nvdb.rl.@Value(identifikasjon.Identifikasjon.lokalId)
    -> TestFilter

Bookmark: Nye meterverdier for segmenterte lenker
Note: Identifiserer lenker som er segmentert
TestFilter
    DEFAULT_VALUE = <UNFILTERED>
    TEST_LIST:
      BOOL_OP,OR,COMPOSITE_TEST,<Unused>,TEST_CLAUSE,"TEST @Value(orgLenkeFraPos) != @Value(startposisjon)
      TEST @Value(orgLenkeTilPos) != @Value(sluttposisjon)",NyMeterverdi
    NyMeterverdi -> AttributeExposer_4
    NyMeterverdi -> FeatureMerger [REQUESTOR]
    <UNFILTERED> -> AttributeManager_15
AttributeExposer_4
    ATTR_LIST = vegreferanse.Vegreferanse.veglenkeMeterFra,vegreferanse.Vegreferanse.veglenkeMeterTil
    -> AttributeManager_10
AttributeManager_10
    ATTR_TABLE:
      SET_TO _startPos = @Value(startposisjon)
      SET_TO _sluttPos = @Value(sluttposisjon)
    -> StringFormatter_4
StringFormatter_4
    FORMAT = .6f
    SRC_ATTRS = _startPos,_sluttPos
    -> HTTPCaller_2
Note: Henter nye meterverdier for lenker som er segmentert
HTTPCaller_2
    CONNECTION_TIMEOUT_LENGTH = 60
    CUSTOM_HEADERS = Accept;application/vnd.vegvesen.nvdb-v2+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = https://www.vegvesen.no/nvdb/api/v2/veg/batch?veglenker=@Value(_startPos)@@Value(lenkesekvensid),@Value(_sluttPos)@@Value(lenkesekvensid)
    TRANSFER_TIMEOUT_LENGTH = 90
    USE_COOKIES = No
    VERIFY_SSL_CERTIFICATES = Yes
    -> XMLFragmenter
XMLFragmenter
    ATTRIBUTE_XML = _url_contents
    EMBEDDED_EXPRESSIONS = posisjoner
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = resultat{}.posisjon.vegreferanse.meter
    XML_SOURCE_TYPE = Attribute with XML document
    FRAGMENTS -> ListIndexer
Note: FraMeter
ListIndexer
    INDEX = 0
    LIST_ATTR = resultat{}
    PREFIX = _fra
    -> ListIndexer_2
Note: TilMeter
ListIndexer_2
    INDEX = 1
    LIST_ATTR = resultat{}
    PREFIX = _til
    -> AttributeKeeper_3
AttributeKeeper_3
    KEEP_ATTRS = vegreferanse.Vegreferanse.veglenkeMeterTil,vegreferanse.Vegreferanse.veglenkeMeterFra,_fraposisjon.vegreferanse.meter,_tilposisjon.vegreferanse.meter,identifikasjon.Identifikasjon.lokalId
    -> AttributeManager_11
AttributeManager_11
    -> FeatureMerger [SUPPLIER]
FeatureMerger
    ATTR_ACCUM_MODE = Merge Supplier
    ATTR_CONFLICT_RES = Use Supplier
    CLEANING_TOLERANCE = None
    IGNORE_NULLS = No
    JOIN_KEYS = @Value(identifikasjon.Identifikasjon.lokalId) @Value(identifikasjon.Identifikasjon.lokalId) AUTO
    MERGE_TYPE = Attributes Only
    PROCESS_DUPS = No
    REJECT_NULL_MISSING_KEYS = No
    SUPPLIERS_FIRST = No
    MERGED -> AttributeManager_15

Bookmark: Vegreferansedato på detaljerte lenker
AttributeManager_17
    ATTR_TABLE:
      SET_TO vegkategori = @Value(vegreferanse.Vegreferanse.vegkategori)
      SET_TO vegnummer = @Value(vegreferanse.Vegreferanse.vegnummer)
      SET_TO vegstatus = @Value(vegreferanse.Vegreferanse.vegstatus)
      SET_TO hovedparsell = @Value(vegreferanse.Vegreferanse.hovedparsell)
      SET_TO veglenkeMeterFra = @Value(vegreferanse.Vegreferanse.veglenkeMeterFra)
      SET_TO veglenkeMeterTil = @Value(vegreferanse.Vegreferanse.veglenkeMeterTil)
    -> FeatureMerger_2 [REQUESTOR]
AttributeKeeper_4
    KEEP_ATTRS = vegreferanse.Vegreferanse.vegkategori,vegreferanse.Vegreferanse.kommunenummer,lenkesekvens.Lenkesekvensreferanse.identifikasjon.Identifikasjon.lokalId,vegreferanse.Vegreferanse.vegreferanseFraDato,vegreferanse.Vegreferanse.vegstatus,vegreferanse.Vegreferanse.hovedparsell,vegreferanse.Vegreferanse.veglenkeMeterTil,vegreferanse.Vegreferanse.vegnummer,vegreferanse.Vegreferanse.referanseretning,vegreferanse.Vegreferanse.veglenkeMeterFra
    -> GeometryRemover
GeometryRemover
    -> FeatureMerger_2 [SUPPLIER]
FeatureMerger_2
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(foreldrelenkeid) @Value(lenkesekvens.Lenkesekvensreferanse.identifikasjon.Identifikasjon.lokalId) AUTO @Value(vegreferanse.Vegreferanse.vegkategori) @Value(vegreferanse.Vegreferanse.vegkategori) AUTO @Value(vegreferanse.Vegreferanse.vegstatus) @Value(vegreferanse.Vegreferanse.vegstatus) AUTO @Value(vegreferanse.Vegreferanse.vegnummer) @Value(vegreferanse.Vegreferanse.vegnummer) AUTO @Value(vegreferanse.Vegreferanse.hovedparsell) @Value(vegreferanse.Vegreferanse.hovedparsell) AUTO
    MERGE_TYPE = Attributes Only
    PROCESS_DUPS = YES
    REJECT_NULL_MISSING_KEYS = No
    SUPPLIERS_FIRST = No
    MERGED -> NullAttributeMapper_4
    UNMERGED_REQUESTOR -> FeatureMerger_2_UnmergedRequestor
    UNMERGED_REQUESTOR -> NullAttributeMapper_4
NullAttributeMapper_4
    ATTRCHOICE = All Attributes
    NULL_TREATMENT = Missing
    SOURCE_ATTR_VAL = Empty Null
    -> GeometryPropertySetter_2
FeatureMerger_2_UnmergedRequestor: Inspector

Bookmark: Svingerestriksjon
ListIndexer_3
    INDEX = 0
    LIST_ATTR = lineærPosisjon{}
    PREFIX = svingeforbudFra.
    -> ListIndexer_4
Note: Håndtering av Svingrestriksjon, som har to LR-posisjoner.
ListIndexer_4
    INDEX = 1
    LIST_ATTR = lineærPosisjon{}
    PREFIX = svingeforbudTil.
    -> AttributeRemover_2
AttributeRemover_2
    LIST_ATTRS = lineærPosisjon{}
    -> AttributeExposer_5
AttributeExposer_5
    ATTR_LIST = fraLineærPosisjonPunkt.lenkesekvens.Identifikasjon.lokalId,fraLineærPosisjonPunkt.lenkesekvens.Identifikasjon.navnerom,fraLineærPosisjonPunkt.posisjon,tilLineærPosisjonPunkt.lenkesekvens.Identifikasjon.lokalId,tilLineærPosisjonPunkt.lenkesekvens.Identifikasjon.navnerom,tilLineærPosisjonPunkt.posisjon
    -> AttributeManager_12
AttributeManager_12
    ATTR_TABLE:
      REMOVE fraLineærPosisjonPunkt.lenkesekvens.Identifikasjon.lokalId
      REMOVE fraLineærPosisjonPunkt.lenkesekvens.Identifikasjon.navnerom
      REMOVE fraLineærPosisjonPunkt.posisjon
      REMOVE tilLineærPosisjonPunkt.lenkesekvens.Identifikasjon.lokalId
      REMOVE tilLineærPosisjonPunkt.lenkesekvens.Identifikasjon.navnerom
      REMOVE tilLineærPosisjonPunkt.posisjon
    -> AttributeExposer

Bookmark: Definerer geometriegenskaper
AttributeExposer
    ATTR_LIST = posisjon,senterlinje
    -> GeometryFilter
GeometryFilter
    BREAK_AGG = No
    GEOM_PORT_NAMES = Point Line Area
    POINT -> GeometryPropertySetter
    LINE -> GeometryPropertySetter_4
    AREA -> GeometryPropertySetter_3
GeometryPropertySetter
    GEOM_NAME_FIELD = posisjon
    OVERWRITE_CHOICE = Yes
    SETTYPE_PARAM = Geometry Name
    SET -> ListIndexer_5
Note: Tar bort liste for lr-pos
ListIndexer_5
    INDEX = 0
    LIST_ATTR = lineærPosisjon{}
    PREFIX = lineærPosisjon.
    -> AttributeRemover_3
    <REJECTED> -> AttributeRemover_OUTPUT_-___Value_fme_feature_type_
AttributeRemover_3
    LIST_ATTRS = lineærPosisjon{}
    -> AttributeRemover_OUTPUT_-___Value_fme_feature_type_
GeometryPropertySetter_4
    GEOM_NAME_FIELD = senterlinje
    OVERWRITE_CHOICE = Yes
    SETTYPE_PARAM = Geometry Name
    SET -> AttributeRemover
AttributeRemover
    REMOVE_ATTRS = posisjon
    -> AttributeRemover_OUTPUT_-___Value_fme_feature_type_
GeometryPropertySetter_3
    GEOM_NAME_FIELD = område
    OVERWRITE_CHOICE = Yes
    SETTYPE_PARAM = Geometry Name
    SET -> AttributeRemover_OUTPUT_-___Value_fme_feature_type_
AttributeRemover_OUTPUT_-___Value_fme_feature_type_: Junction
    -> Junction

FME custom transformer NVDB_Vegnettleser
Leser og tolker data fra NVDB-API

Parameters:
- NESTE.HREF = @Value(neste.href)   # neste.href
- OMR = @Value(omr)   # omr
- OMRNVN = @Value(omrNvn)   # omrNvn
- namespace = vegvesen.no.nvdb   # Namespace
- nettverk:   # Python Script
      ns = FME_MacroValues['namespace'] + '.nw.' + FME_MacroValues['OMR'] + '_' + FME_MacroValues['OMRNVN']
      return ns

_Input (input)
    -> HTTPCaller_2
Loop (input)
    -> HTTPCaller_2
HTTPCaller_2
    CONNECTION_TIMEOUT_LENGTH = 60
    CUSTOM_HEADERS = Accept;application/vnd.vegvesen.nvdb-v2+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
Note: Deler opp i en XML pr vegobjekt
XMLFragmenter
    ATTRIBUTE_XML = _url_contents
    EMBEDDED_EXPRESSIONS = lenke
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt startnode sluttnode veglenkeid
    REJECT_FEATURES_WITH_NO_FRAGMENTS = YES
    XML_SOURCE_TYPE = Attribute with XML document
    FRAGMENTS -> StringReplacer
Note: Bytter "-" med "_" i nodeid
StringReplacer
    CASE = NO
    FIND_TEXT = -
    NO_MATCH = _FME_NO_OP_
    REGEXP = NO
    REPLACE_TEXT = _
    SRC_ATTRS = sluttnode,startnode
    -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id epsg detaljnivå lenkesekvens.Lenkesekvensreferanse.startposisjon lenkesekvens.Lenkesekvensreferanse.sluttposisjon startnodeId sluttnodeId temakode veglenkeid vegreferanse.Vegreferanse.kommunenummer konnekteringslenke medium datafangstdato typeVeg kommunenummer lenkesekvens.Lenkesekvensreferanse.identifikasjon.Identifikasjon.lokalId foreldrelenkeid vegreferanse.Vegreferanse.vegkategori vegreferanse.Vegreferanse.vegnummer vegreferanse.Vegreferanse.vegstatus vegreferanse.Vegreferanse.hovedparsell vegreferanse.Vegreferanse.veglenkeMeterFra vegreferanse.Vegreferanse.veglenkeMeterTil vegreferanse.Vegreferanse.referanseretning
    PYTHONSOURCE:
      #!/usr/bin/env python
      # -*- coding: utf-8 -*-
      import fme
      import fmeobjects

      def extractNVDB_XML(feature):

          #Namespace
          ns= 'vegvesen.no.nvdb'

          # Setter feature type
          ft='Veglenke'
          feature.setAttribute('fme_feature_type',ft)
          # ID og versjon.  Namespace ...rls for veglenkesekvenser (id på lenkene er lenkesekvensen sin id pluss et løpenummer)
          feature.setAttribute('identifikasjon.Identifikasjon.navnerom', ns + '.rls')
          feature.setAttribute('lenkesekvens.Lenkesekvensreferanse.identifikasjon.Identifikasjon.navnerom', ns + '.rls')
          v=feature.getAttribute('veglenkeid')
          # feature.setAttribute('NVDB_ID', v)
          feature.setAttribute('identifikasjon.Identifikasjon.lokalId', v)
          feature.setAttribute('lenkesekvens.Lenkesekvensreferanse.identifikasjon.Identifikasjon.lokalId', v)
          feature.setAttribute('gml_id', ns + '.rls.' + v)
          # feature.removeAttribute('veglenkeid')

          # Kommune
          v=feature.getAttribute('kommune')
          feature.setAttribute('kommunenummer', v.zfill(4))
          feature.removeAttribute('kommune')

          #Lineære posisjoner i lenkesekvensen
          feature.setAttribute('standardLRM', 'normalisert')
          # startposisjon og sluttposisjon må tolkes fra evt eksponentielle tall
          v=feature.getAttribute('startposisjon')
          feature.setAttribute('lenkesekvens.Lenkesekvensreferanse.startposisjon', float(v))
          v=feature.getAttribute('sluttposisjon')
          feature.setAttribute('lenkesekvens.Lenkesekvensreferanse.sluttposisjon', float(v))

          v=feature.getAttribute('felt')
          if v != None:
              feature.setAttribute('feltoversikt',v)

          #Topologi
          #detaljnivå
          #    <topologinivå>1</topologinivå>
          #    <topologinivå_tekst>Kjørebane</topologinivå_tekst>
          v=feature.getAttribute(u'topologinivå')
          if v != None:
              #print v
              if v == '0':
                  feature.setAttribute(u'detaljnivå', u'vegtrase')
              if v == '1':
                  feature.setAttribute(u'detaljnivå', u'kjørebane')
              if v == '2':
                  feature.setAttribute(u'detaljnivå', u'kjørefelt')
              feature.removeAttribute(u'topologinivå_tekst')
             #feature.removeAttribute('topologinivå')

          #noder
          #    <startnode>2373197-1</startnode>
          v=str(feature.getAttribute('startnode'))
          feature.removeAttribute('startnode')
          if v != 'None':
              feature.setAttribute('startnode.xlink_href', '#' + ns + '.rn.' + v)
              feature.setAttribute('startnodeId', v)
          #    <sluttnode>1087601-2</sluttnode>
          v=str(feature.getAttribute('sluttnode'))
          feature.removeAttribute('sluttnode')
          if v != 'None':
              feature.setAttribute('sluttnode.xlink_href', '#' + ns + '.rn.' + v)
              feature.setAttribute('sluttnodeId', v)


          #Kvalitet
          #            <metode>60</metode>
          v=str(feature.getAttribute(u'geometri.kvalitet.metode'))
          if v != 'None' and v != '-1':
              feature.setAttribute(u'kvalitet.Posisjonskvalitet.målemetode', v)
          feature.removeAttribute(u'geometri.kvalitet.metode')
          #            <nøyaktighet>200</nøyaktighet>
          v=str(feature.getAttribute(u'geometri.kvalitet.nøyaktighet'))
          if v != 'None' and v != '-1':
              feature.setAttribute(u'kvalitet.Posisjonskvalitet.nøyaktighet', v)
          feature.removeAttribute(u'geometri.kvalitet.nøyaktighet')
          #            <høydenøyaktighet>-1</høydenøyaktighet>
          v=str(feature.getAttribute('geometri.kvalitet.høydenøyaktighet'))
          if v != 'None' and v != '-1':
              feature.setAttribute(u'kvalitet.Posisjonskvalitet.nøyaktighetHøyde', v)
          feature.removeAttribute(u'geometri.kvalitet.høydenøyaktighet')
          #            <toleranse>-1</toleranse>
          v=str(feature.getAttribute(u'geometri.kvalitet.toleranse'))
          if v != 'None' and v != '-1':
              feature.setAttribute(u'kvalitet.Posisjonskvalitet.maksimaltAvvik', v)
          feature.removeAttribute(u'geometri.kvalitet.toleranse')
          #            <synlighet>99</synlighet>
          v=str(feature.getAttribute(u'geometri.kvalitet.synlighet'))
          if v == '0' or v == '1' or v == '2' or v == '3' :
              feature.setAttribute(u'kvalitet.Posisjonskvalitet.synbarhet', v)
          feature.removeAttribute(u'geometri.kvalitet.synlighet')
          #            <datafangstdato>2002-12-07</datafangstdato>
          v=str(feature.getAttribute(u'geometri.kvalitet.datafangstdato'))
          if v != 'None' and v != '-1':
              feature.setAttribute(u'datafangstdato', v)
          feature.removeAttribute(u'geometri.kvalitet.datafangstdato')

          # Geometri
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Vegreferanse
          # <vegreferanse>
          #    <fylke>5</fylke>
          v=str(feature.getAttribute('vegreferanse.fylke'))
          if v != 'None' and v != '0':
              feature.setAttribute('vegreferanse.Vegreferanse.fylkesnummer', v.zfill(2))
          feature.removeAttribute('vegreferanse.fylke')
          #    <kommune>520</kommune>
          v=str(feature.getAttribute('vegreferanse.kommune'))
          if v != 'None' and v != '0':
              feature.setAttribute('vegreferanse.Vegreferanse.kommunenummer', v.zfill(4))
          feature.removeAttribute('vegreferanse.kommune')
          #    <kategori>K</kategori>
          v=str(feature.getAttribute('vegreferanse.kategori'))
          if v != 'None':
              feature.setAttribute('vegreferanse.Vegreferanse.vegkategori', v)
          feature.removeAttribute('vegreferanse.kategori')
          #    <status>V</status>
          v=str(feature.getAttribute('vegreferanse.status'))
          if v != 'None':
              feature.setAttribute('vegreferanse.Vegreferanse.vegstatus', v)
          feature.removeAttribute('vegreferanse.status')
          #    <nummer>1161</nummer>
          v=str(feature.getAttribute('vegreferanse.nummer'))
          if v != 'None':
              feature.setAttribute('vegreferanse.Vegreferanse.vegnummer', v)
          feature.removeAttribute('vegreferanse.nummer')
          #    <hp>1</hp>
          v=str(feature.getAttribute('vegreferanse.hp'))
          if v != 'None':
              feature.setAttribute('vegreferanse.Vegreferanse.hovedparsell', v)
          feature.removeAttribute('vegreferanse.hp')
          #    <fra_meter>57</fra_meter>
          f=str(feature.getAttribute('vegreferanse.fra_meter'))
          if f != 'None':
              feature.setAttribute('vegreferanse.Vegreferanse.veglenkeMeterFra', f)
          feature.removeAttribute('vegreferanse.fra_meter')
          #    <til_meter>96</til_meter>
          t=str(feature.getAttribute('vegreferanse.til_meter'))
          if t != 'None':
              feature.setAttribute('vegreferanse.Vegreferanse.veglenkeMeterTil', t)
          feature.removeAttribute('vegreferanse.til_meter')
          #    <kortform>0520 Kv1161 hp1 m57-96</kortform>
          if f!='None' and t!='None':
              if int(f) <= int(t):
                  feature.setAttribute('vegreferanse.Vegreferanse.referanseretning', 'med')
              else:
                  feature.setAttribute('vegreferanse.Vegreferanse.referanseretning', 'mot')
          # </vegreferanse>
    PYTHONSYMBOL = extractNVDB_XML
    -> ListBuilder
ListBuilder
    GRP_BY = identifikasjon.Identifikasjon.lokalId identifikasjon.Identifikasjon.navnerom gml_id identifikasjon.Identifikasjon.versjonId
    LIST_NAME = _linkList
    -> ListSorter
ListSorter
    ORDER = Ascending
    SRC_LIST = _linkList{}.lenkesekvens.Lenkesekvensreferanse.sluttposisjon
    TYPE = Numeric
    -> AttributeCreator
AttributeCreator
    ATTR_TABLE = SET_TO nettverk{0}.xlink_href = #$(nettverk)
    -> Veglenkereferanser
Note: Lager id for Veglenker + referanser fra Veglenkesekvens til Veglenke
Veglenkereferanser: PythonCaller
    NEW_ATTRIBUTES = lenke{}
    PYTHONSOURCE:
      import fme
      import fmeobjects

      def setLinkID(feature):

          # Namespace ..rl for veglenker
          ns= 'vegvesen.no.nvdb.rl'

          ft='Veglenkesekvens'
          feature.setAttribute('fme_feature_type',ft)

          i = 0
          while True:
              v = feature.getAttribute('_linkList{%d}.identifikasjon.Identifikasjon.lokalId' % i)
              if v == None:
                  break
              localId = str(v) + "_" + str(i)
              feature.setAttribute('_linkList{%d}.identifikasjon.Identifikasjon.lokalId' % i, localId)
              feature.setAttribute('_linkList{%d}.identifikasjon.Identifikasjon.navnerom' % i, ns)
              gml_id = ns + "." + localId
              feature.setAttribute('_linkList{%d}.gml_id' % i, gml_id)

              f=feature.getAttribute('_linkList{%d}.startposisjon' % i)
              t=feature.getAttribute('_linkList{%d}.sluttposisjon' % i)
              if f < t:
                  feature.setAttribute('lenke{%d}.RettaLenke.retning' % i, 'med')
              else:
                  feature.setAttribute('lenke{%d}.RettaLenke.retning' % i, 'mot')
              feature.setAttribute('lenke{%d}.RettaLenke.lenke.xlink_href' % i, '#' + gml_id)
              i += 1
    PYTHONSYMBOL = setLinkID
    -> Veglenkesekvens (output)
    -> ListExploder
Veglenkesekvens (output)
ListExploder
    ATTR_ACCUM_MODE = Merge Incoming List
    ATTR_CONFLICT_RES = Use Incoming List
    INDEX_ATTR = _element_index
    LIST_ATTR = _linkList{}
    ELEMENTS -> GeometryReplacer
Note: Geometri
GeometryReplacer
    KIND_LONG = OGC Well Known Text
    OGC_WKT_PRECISION_DISPLAY = 64-bit
    REMOVE_ATTRIBUTE = Yes
    SOURCE = @Value(geometri)
    -> 3DForcer
3DForcer
    KEEPZVAL = Yes
    ZVALATTR = NaN
    -> CoordinateSystemSetter
CoordinateSystemSetter
    COORDSYS = EPSG:6173
    -> GeometryPropertySetter_4
    -> AttributeManager_2
    -> AttributeManager_3
Note: Definerer geometriegenskap
GeometryPropertySetter_4
    GEOM_NAME_FIELD = senterlinje
    OVERWRITE_CHOICE = Yes
    SETTYPE_PARAM = Geometry Name
    SET -> DateFormatter
DateFormatter
    DATE_ATTR = datafangstdato
    FMT = ISO Date (%Y-%m-%d)
    INVALID_DATE_VALUE = 0001-01-01
    SRCFMT = Unknown - Automatic Detection
    -> AttributeValueMapper
    -> NullAttributeMapper
Note: Oversetter medium fra initialverdier til kodetekst
AttributeValueMapper [off]
    DEFAULT_VALUE = _FME_NO_OP_
    DIRECTION = Forward (Source To Destination)
    LUT = B,iBygning,D,tidvisUnderVann,I,påIsbre,J,underIsbre,L,iLuft,O,påVannoverflaten,S,påSjøbunnen,T,påTerrenget,U,underTerrenget,V,alltidIVann,W,underSjøbunnen,X,ukjent
    SRC = medium
    VAL_ATTR = medium
    -> AttributeValueMapper_2 [off]
Note: Oversetter synbarhet fra initialverdier til kodetekst
AttributeValueMapper_2 [off]
    DEFAULT_VALUE = _FME_NO_OP_
    DIRECTION = Forward (Source To Destination)
    LUT = 0,fulltSynligOgGjenfinnbarITerrenget,1,dårligGjenfinnbarITerrenget,2,middelsSynligIFlybilde,3,dårligSynligIFlybilde
    SRC = kvalitet.Posisjonskvalitet.synbarhet
    VAL_ATTR = kvalitet.Posisjonskvalitet.synbarhet
    -> AttributeRemover
NullAttributeMapper
    ATTRCHOICE = Selected Attributes
    ATTRLIST = datafangstdato
    NEW_VALUE = 0001-01-01
    NULL_TREATMENT = New Value
    SOURCE_ATTR_VAL = Null Empty "Missing (Selected Attributes Only)"
    -> AttributeRemover
AttributeRemover
    LIST_ATTRS = lenke{}
    -> Veglenke (output)
Veglenke (output)
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    REJECT_FEATURES_WITH_NO_FRAGMENTS = YES
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)
Creator
    GEOMTYPE = Geometry Object
    NUM = 1
    CREATED -> AttributeManager
AttributeManager
    ATTR_TABLE:
      REMOVE _creation_instance
      SET_TO nettverksnavn = NVDB
      SET_TO fme_feature_type = Nettverk
      SET_TO gml_id = $(nettverk)
    -> Nettverk (output)
Nettverk (output)

Bookmark: Lager unike noder
AttributeManager_2
    ATTR_TABLE = RENAME_SET_VALUE startnodeId > nodeId
    -> CoordinateExtractor_2
CoordinateExtractor_2
    IND = 0
    MODE = Specify Coordinate
    X_ATTR = _x
    Y_ATTR = _y
    Z_ATTR = _z
    -> AttributeKeeper
AttributeManager_3
    ATTR_TABLE = RENAME_SET_VALUE sluttnodeId > nodeId
    -> CoordinateExtractor
CoordinateExtractor
    IND = -1
    MODE = Specify Coordinate
    X_ATTR = _x
    Y_ATTR = _y
    Z_ATTR = _z
    -> AttributeKeeper
AttributeKeeper
    KEEP_ATTRS = _y,_x,identifikasjon.Identifikasjon.navnerom,nodeId,_z
    -> DuplicateFilter
DuplicateFilter
    INPUT_ORDERED_CHOICE = No
    KEYATTR = nodeId
    UNIQUE -> VertexCreator
Note: Lager nodepunkt
VertexCreator
    MODE_NAME = Replace with Point
    XVAL = @Value(_x)
    YVAL = @Value(_y)
    ZVAL = @Value(_z)
    -> GeometryPropertySetter_2
Note: Definerer geometriegenskap
GeometryPropertySetter_2
    GEOM_NAME_FIELD = posisjon
    OVERWRITE_CHOICE = Yes
    SETTYPE_PARAM = Geometry Name
    SET -> AttributeManager_4
Note: Lager nodeid
AttributeManager_4
    ATTR_TABLE:
      RENAME_SET_VALUE nodeId > identifikasjon.Identifikasjon.lokalId
      REMOVE _x
      REMOVE _y
      REMOVE _z
      SET_TO identifikasjon.Identifikasjon.navnerom = $(namespace).rn
      SET_TO gml_id = $(namespace).rn.@Value(identifikasjon.Identifikasjon.lokalId)
      SET_TO fme_feature_type = Vegnode
    -> Vegnode (output)
Vegnode (output)

FME custom transformer Segments
Creates a list of segments with RoladLinkID, from meassure and to-meassure from an overlay between event tables

Parameters:
- RoadLinkID =   # " " RoadLinkID
- FromVal =   # " " FromVal
- ToVal =   # " " ToVal

Event_Tables (input)
    -> AttributeCreator_2
Note: Loop for creating unique table of segments
UniqeSegments
    __COMPOUND_PARAMETERS = -
    Unique_Segments -> AttributeManager
AttributeManager
    ATTR_TABLE = SET_TO _SegId = @Value(RoadLinkID)_@Value(FromVal)_@Value(ToVal)
    -> Unique_Segment_List (output)
Unique_Segment_List (output)

Bookmark: Link ID and meassure attributes
AttributeCreator_2
    ATTR_TABLE:
      SET_TO RoadLinkID = $(RoadLinkID)
      SET_TO FromVal = $(FromVal)
      SET_TO ToVal = $(ToVal)
    -> AttributeKeeper
AttributeKeeper
    KEEP_ATTRS = RoadLinkID,FromVal,ToVal
    -> ATTRIBUTERENAMER_3
    -> ATTRIBUTERENAMER_4

Bookmark: Create a list of all unique breakpoints pr RoadLinkID
Note: From
ATTRIBUTERENAMER_3: AttributeRenamer
    ATTR_TABLE = RENAME_SET_DEFAULT FromVal > BREAKPOINT
    -> AttributeKeeper_2
Note: To
ATTRIBUTERENAMER_4: AttributeRenamer
    ATTR_TABLE = RENAME_SET_DEFAULT ToVal > BREAKPOINT
    -> AttributeKeeper_2
AttributeKeeper_2
    KEEP_ATTRS = RoadLinkID,BREAKPOINT
    -> DuplicateFilter
DuplicateFilter
    INPUT_ORDERED_CHOICE = No
    KEYATTR = RoadLinkID BREAKPOINT
    UNIQUE -> ListBuilder
ListBuilder
    GRP_BY = RoadLinkID
    LIST_NAME = _Bp_list
    -> ListSorter
ListSorter
    ORDER = Ascending
    SRC_LIST = _Bp_list{}.BREAKPOINT
    TYPE = Numeric
    -> ListElementCounter
ListElementCounter
    CNT_ATTR = _element_count
    LIST_NAME = _Bp_list{}
    -> AttributeManager_2
AttributeManager_2
    ATTR_TABLE:
      SET_TO _maxIdx = @Evaluate(@Evaluate(@Value(_element_count)-1))
      REMOVE _element_count
      SET_TO _idx = 0
    -> UniqeSegments [BREAKPOINTLIST]

FME custom transformer EventOverlayer

Parameters:
- RoadLinkID =   # " " RoadLinkID
- FromVal =   # " " FromVal
- ToVal =   # " " ToVal

Event_table_A (input)
    -> AttributeCreator_2
AttributeCreator_2
    ATTR_TABLE:
      SET_TO RoadLinkID = $(RoadLinkID)
      SET_TO FromVal = $(FromVal)
      SET_TO ToVal = $(ToVal)
    -> StringFormatter
Note: Avrunder til 8 desimaler for å unngå / problem med eksponentialverdier
StringFormatter
    FORMAT = .8f
    SRC_ATTRS = FromVal,ToVal
    -> GeometryRemover
GeometryRemover
    -> SegmentizeTable [Events]
    -> Segments [Event_Tables]
Event_table_B (input)
    -> AttributeCreator_3
AttributeCreator_3
    ATTR_TABLE:
      SET_TO RoadLinkID = $(RoadLinkID)
      SET_TO FromVal = $(FromVal)
      SET_TO ToVal = $(ToVal)
    -> StringFormatter_2
Note: Avrunder til 8 desimaler for å unngå / problem med eksponentialverdier
StringFormatter_2
    FORMAT = .8f
    SRC_ATTRS = FromVal,ToVal
    -> GeometryRemover_2
GeometryRemover_2
    -> Segments [Event_Tables]
    -> SegmentizeTable_2 [Events]
Note: Common segments
Segments
    FromVal = @Value(FromVal)
    RoadLinkID = @Value(RoadLinkID)
    ToVal = @Value(ToVal)
    __COMPOUND_PARAMETERS = -
    Unique_Segment_List -> SegmentizeTable [SegmentList]
    Unique_Segment_List -> SegmentizeTable_2 [SegmentList]
Note: Segmentize table A
SegmentizeTable
    __COMPOUND_PARAMETERS = -
    eventFromVal = @Value(FromVal)
    eventRoadLink = @Value(RoadLinkID)
    eventToVal = @Value(ToVal)
    Segmented -> FeatureMerger [REQUESTOR]
Note: Segmentize table B
SegmentizeTable_2
    __COMPOUND_PARAMETERS = -
    eventFromVal = @Value(FromVal)
    eventRoadLink = @Value(RoadLinkID)
    eventToVal = @Value(ToVal)
    Segmented -> FeatureMerger [SUPPLIER]
Note: Merge segments
FeatureMerger
    ATTR_ACCUM_MODE = Merge Supplier
    ATTR_CONFLICT_RES = Use Requestor
    IGNORE_NULLS = No
    JOIN_KEYS = @Value(_SegId) @Value(_SegId) AUTO
    MERGE_TYPE = Attributes Only
    PROCESS_DUPS = No
    REJECT_NULL_MISSING_KEYS = No
    SUPPLIERS_FIRST = No
    MERGED -> Common_Segments (output)
    NOT_MERGED -> Only_A (output)
    UNREFERENCED -> Only_B (output)
Common_Segments (output)
Only_A (output)
Only_B (output)

FME custom transformer EventGeometry

Parameters:
- _rlRouteID =   # Network RouteID attribute
- _rlFrom =   # Network From measure attribute
- _rlTo =   # Network To measure attribute
- _eventRouteID =   # Event Route ID attribute
- _eventFrom =   # Event From Measure attribute
- _eventTo =   # Event To measure attribute
- _measureMode = 3D   # Measurement Mode
- _dimension = 3   # Length Dimension

Network (input)
    -> AttributeCreator
AttributeCreator
    ATTR_LIST = _routeID,$(_rlRouteID),_rlFrom,$(_rlFrom),_rlTo,$(_rlTo)
    -> StringFormatter_3
Note: Avrunder til 8 desimaler for å unngå / problem med eksponentialverdier
StringFormatter_3
    FORMAT = .8f
    SRC_ATTRS = _rlFrom,_rlTo
    -> InlineQuerier [ROADLINKS]
Events (input)
    -> Counter
Counter
    CNT_ATTR = _eventID
    DOMAIN = counter
    SCOPE = Global
    START = 0
    -> AttributeCreator_2
AttributeCreator_2
    ATTR_LIST = _routeID,$(_eventRouteID),_eventFrom,$(_eventFrom),_eventTo,$(_eventTo)
    -> StringFormatter_2
Note: Avrunder til 8 desimaler for å unngå / problem med eksponentialverdier
StringFormatter_2
    FORMAT = .8f
    SRC_ATTRS = _eventFrom,_eventTo
    -> InlineQuerier [EVENTS]
Note: Select road segements within / the measure of the events
InlineQuerier
    QUERY_DEF:
      SEGMENTS,SELECT * FROM ROADLINKS
      INNER JOIN EVENTS ON ROADLINKS._routeID = EVENTS._routeID
      WHERE (ROADLINKS._rlFrom < EVENTS._eventTo AND ROADLINKS._rlTo > EVENTS._eventFrom)
      OR (ROADLINKS._rlFrom = EVENTS._eventFrom AND EVENTS._eventFrom = EVENTS._eventTo)
      OR (ROADLINKS._rlTo = EVENTS._eventTo AND EVENTS._eventFrom = EVENTS._eventTo),FIRST
    QUERY_SCHEMA = SEGMENTS,_routeID,varchar(38),_rlFrom,float,_rlTo,float,ROADLINKS.fme_feature_content,fme_feature_content,_eventID,varchar(38),_eventFrom,float,_eventTo,float,EVENTS.fme_feature_content,fme_feature_content
    TABLE_DEF = ROADLINKS,_routeID,varchar(38),_rlFrom,float,_rlTo,float,EVENTS,_eventID,varchar(38),_routeID,varchar(38),_eventFrom,float,_eventTo,float
    SEGMENTS -> LengthCalculator
Note: Calculate segment length
LengthCalculator
    DIM = $(_dimension)
    LEN_ATTR = _length
    MULT = 1
    -> ExpressionEvaluator
Note: Calculate scale
ExpressionEvaluator
    EXPRESSION = @Value(_length)/((@Value(_rlTo)-@Value(_rlFrom))+0.000)
    VAL_ATTR = _scale
    -> TestFilter_3
Note: Filter on what part of / the segment to be snipped
TestFilter_3
    DEFAULT_VALUE = <UNFILTERED>
    TEST_LIST:
      BOOL_OP,OR,COMPOSITE_TEST,<Unused>,TEST_CLAUSE,"TEST ""@Value(_eventFrom)"" = ""@Value(_eventTo)""",Point events,BOOL_OP,AND,COMPOSITE_TEST,<Unused>,TEST_CLAUSE,"TEST ""@Value(_rlFrom)"" < ""@Value(_eventFrom)""
      TEST ""@Value(_rlTo)"" > ""@Value(_eventTo)""",Within segment,BOOL_OP,AND,COMPOSITE_TEST,<Unused>,TEST_CLAUSE,"TEST ""@Value(_rlFrom)"" >= ""@Value(_eventFrom)""
      TEST ""@Value(_rlTo)"" > ""@Value(_eventTo)""",Start of segment,BOOL_OP,AND,COMPOSITE_TEST,<Unused>,TEST_CLAUSE,"TEST ""@Value(_rlFrom)"" < ""@Value(_eventFrom)""
      TEST ""@Value(_rlTo)"" <= ""@Value(_eventTo)""",End of segment,BOOL_OP,AND,COMPOSITE_TEST,<Unused>,TEST_CLAUSE,"TEST ""@Value(_rlFrom)"" >= ""@Value(_eventFrom)""
      TEST ""@Value(_rlTo)"" <= ""@Value(_eventTo)""",Complete segment
    Point events -> ExpressionEvaluator_2
    Within segment -> ExpressionEvaluator_3
    Start of segment -> ExpressionEvaluator_6
    End of segment -> ExpressionEvaluator_5
    Complete segment -> AttributeRemover
AttributeRemover
    REMOVE_ATTRS = _rlFrom,_rlTo,_scale,_snip,_x,_y,_z,_snipFrom,_snipTo
    -> GeometryFilter
GeometryFilter
    BREAK_AGG = No
    POINT -> Points (output)
    LINE -> Lines (output)
Points (output)
Lines (output)

Bookmark: Point events
Note: Calculate position
ExpressionEvaluator_2
    EXPRESSION = (@Value(_eventFrom)-@Value(_rlFrom))*@Value(_scale)
    VAL_ATTR = _snip
    -> Snipper
Note: Snip start of segment
Snipper
    ENDLOCATIONATTR = -1
    MEASUREMENTTYPE = $(_measureMode)
    SNIPMODE = Distance (Value)
    STARTLOCATIONATTR = @Value(_snip)
    -> CoordinateExtractor
Note: Get start coordinates
CoordinateExtractor
    IND = 0
    X_ATTR = _x
    Y_ATTR = _y
    Z_ATTR = _z
    Z_DEFAULT = -9999
    -> 3DPointReplacer
Note: Replace geometry with point coordinates
3DPointReplacer
    XVALATTR = @Value(_x)
    YVALATTR = @Value(_y)
    ZVALATTR = @Value(_z)
    POINT -> AttributeRemover

Bookmark: Events that are within a segment
Note: Calculate snip from
ExpressionEvaluator_3
    EXPRESSION = (@Value(_eventFrom)-@Value(_rlFrom))*@Value(_scale)
    VAL_ATTR = _snipFrom
    -> ExpressionEvaluator_4
Note: Calculate snip to
ExpressionEvaluator_4
    EXPRESSION = (@Value(_eventTo)-@Value(_rlFrom))*@Value(_scale)
    VAL_ATTR = _snipTo
    -> Snipper_2
Note: Snip segment
Snipper_2
    ENDLOCATIONATTR = @Value(_snipTo)
    MEASUREMENTTYPE = $(_measureMode)
    SNIPMODE = Distance (Value)
    STARTLOCATIONATTR = @Value(_snipFrom)
    -> AttributeRemover

Bookmark: Events that are on the start of a segment
Note: Calculate snip to
ExpressionEvaluator_6
    EXPRESSION = (@Value(_eventTo)-@Value(_rlFrom))*@Value(_scale)
    VAL_ATTR = _snipTo
    -> Snipper_3
Note: Snip segment
Snipper_3
    ENDLOCATIONATTR = @Value(_snipTo)
    MEASUREMENTTYPE = $(_measureMode)
    SNIPMODE = Distance (Value)
    STARTLOCATIONATTR = 0
    -> AttributeRemover

Bookmark: Events that are on the end of a segment
Note: Calculate snip from
ExpressionEvaluator_5
    EXPRESSION = (@Value(_eventFrom)-@Value(_rlFrom))*@Value(_scale)
    VAL_ATTR = _snipFrom
    -> Snipper_4
Note: Snip segment
Snipper_4
    ENDLOCATIONATTR = -1
    MEASUREMENTTYPE = $(_measureMode)
    SNIPMODE = Distance (Value)
    STARTLOCATIONATTR = @Value(_snipFrom)
    -> AttributeRemover

FME custom transformer UniqeSegments

BREAKPOINTLIST (input)
    -> AttributeExposer_3
AttributeExposer_3
    ATTR_LIST = _idx,_maxIdx,RoadLinkID,_Bp_list{}.BREAKPOINT,_Bp_list{}.RoadLinkID,_Bp_list{}.fme_feature_type,_Bp_list{}.fme_basename,_Bp_list{}.fme_dataset
    -> ListIndexer

Bookmark: From value
ListIndexer
    INDEX = @Value(_idx)
    LIST_ATTR = _Bp_list{}
    -> AttributeExposer
AttributeExposer
    ATTR_LIST = BREAKPOINT
    -> AttributeManager
AttributeManager
    ATTR_TABLE:
      RENAME_SET_VALUE BREAKPOINT > FromVal
      SET_TO _next = @Evaluate(@Value(_idx)+1)
    -> ListIndexer_2

Bookmark: To value
ListIndexer_2
    INDEX = @Value(_next)
    LIST_ATTR = _Bp_list{}
    -> AttributeExposer_2
AttributeExposer_2
    ATTR_LIST = BREAKPOINT
    -> AttributeManager_2
AttributeManager_2
    ATTR_TABLE:
      RENAME_SET_VALUE BREAKPOINT > ToVal
      SET_TO _next = @Evaluate(@Value(_idx)+1)
    -> AttributeManager_3
    -> TestFilter

Bookmark: Finished segements
AttributeManager_3
    ATTR_TABLE:
      REMOVE _idx
      REMOVE _maxIdx
      REMOVE _next
      REMOVE _Bp_list{}.BREAKPOINT
      REMOVE _Bp_list{}.RoadLinkID
      REMOVE _Bp_list{}.fme_feature_type
      REMOVE _Bp_list{}.fme_basename
      REMOVE _Bp_list{}.fme_dataset
    -> Unique_Segments (output)
Unique_Segments (output)

Bookmark: Test for more segments
TestFilter
    DEFAULT_VALUE = <UNFILTERED>
    TEST_LIST = BOOL_OP,OR,COMPOSITE_TEST,<Unused>,TEST_CLAUSE,"TEST @Value(_next) = @Value(_maxIdx)",Last
    <UNFILTERED> -> AttributeCreator
AttributeCreator
    ATTR_TABLE = SET_TO _idx = @Value(_next)
    -> BREAKPOINTLIST (output)
BREAKPOINTLIST (output)

FME custom transformer SegmentizeTable
Splits an event table based on a list of segments with from-to-measure

Parameters:
- eventRoadLink =   # Event Table Road Link ID Attribute
- eventFromVal =   # Event Table from meassure
- eventToVal =   # Event Table To Meassure

Events (input)
    -> AttributeCreator
SegmentList (input)
    -> AttributeExposer
Note: Create common segments
InlineQuerier
    QUERY_DEF:
      EventSegments,Select * FROM Events
      INNER JOIN Segments ON Events.RoadLinkID = Segments.RoadLinkID
      WHERE (Segments.segFromVal < Events.eventToVal AND Segments.segToVal > Events.eventFromVal),FIRST
    QUERY_SCHEMA = EventSegments,RoadLinkID,varchar(30),eventFromVal,float,eventToVal,float,Events.fme_feature_content,fme_feature_content,segFromVal,float,segToVal,float,Segments.fme_feature_content,fme_feature_content
    TABLE_DEF = Events,RoadLinkID,varchar(30),eventFromVal,float,eventToVal,float,Segments,RoadLinkID,varchar(30),segFromVal,float,segToVal,float
    EventSegments -> AttributeManager
AttributeManager
    ATTR_TABLE:
      SET_TO FromVal = @Value(segFromVal)
      SET_TO ToVal = @Value(segToVal)
      REMOVE eventFromVal
      REMOVE eventToVal
      REMOVE segFromVal
      REMOVE segToVal
    -> Segmented (output)
Segmented (output)

Bookmark: Link ID and measure attributes
AttributeCreator
    ATTR_TABLE:
      SET_TO RoadLinkID = $(eventRoadLink)
      SET_TO eventFromVal = $(eventFromVal)
      SET_TO eventToVal = $(eventToVal)
    -> InlineQuerier [Events]
AttributeExposer
    ATTR_LIST = RoadLinkID,FromVal,ToVal
    -> AttributeExpressionRenamer
AttributeExpressionRenamer: BulkAttributeRenamer
    ATTRCHOICE = Selected Attributes
    ATTRLIST = FromVal ToVal
    MODE_CHOICE = RENAME
    PATTERN_ACTION_DISP = ADDPREFIX
    REPLACE_STR = seg
    -> InlineQuerier [Segments]

FME custom transformer NVDB_Leser
Leser og tolker data fra NVDB-API

Parameters:
- NESTE.HREF = @Value(neste.href)   # neste.href

_Input (input)
    -> HTTPCaller_2
Loop (input)
    -> HTTPCaller_2
HTTPCaller_2
    CONNECTION_TIMEOUT_LENGTH = 60
    CUSTOM_HEADERS = Accept;application/vnd.vegvesen.nvdb-v2+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
Note: Kan det defineres at et element SKAL blli en liste? Vil i så fall kunne forenkle koden i NVDBTranslator mye. / Se under cardinality under dokumentasjon i XML Fragmenter
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt
    XML_SOURCE_TYPE = Attribute with XML document
    FRAGMENTS -> NVDBTranslator_2
Note: Oversetter fra NVDB-API-XML
NVDBTranslator_2: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg lineærPosisjon{}.LineærPosisjonStrekning.veglenkeid lineærPosisjon{}.LineærPosisjonStrekning.fraPosisjon lineærPosisjon{}.LineærPosisjonStrekning.tilPosisjon kommunenummer
    PYTHONSOURCE:
      import fme
      import fmeobjects

      def extractNVDB_XML(feature):

          ns='vegvesen.no.nvdb' # FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Kommune
          v=feature.getAttribute('lokasjon.kommuner.kommune')
          feature.setAttribute('kommunenummer', v.zfill(4))
          feature.removeAttribute('lokasjon.kommuner.kommune')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      # if (n == 'Kommunenummer' and v == 0):
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute(u'lineærPosisjon{%d}.LineærPosisjonStrekning.nettverkselement.xlink_href' % i, 'Veglenke.gml#' + ns + '.rl.' + v)
                              feature.setAttribute(u'lineærPosisjon{%d}.LineærPosisjonStrekning.veglenkeid' % i, v)
                              feature.setAttribute(u'lineærPosisjon{%d}.LineærPosisjonStrekning.lenkesekvens.Identifikasjon.navnerom' % i, ns + '.rls')
                              feature.setAttribute(u'lineærPosisjon{%d}.LineærPosisjonStrekning.lenkesekvens.Identifikasjon.lokalId' % i, v)
                          v = str(feature.getAttribute('lokasjon.stedfestinger.stedfesting.fra_posisjon'))
                          if v != 'None':
                              feature.setAttribute(u'lineærPosisjon{%d}.LineærPosisjonStrekning.fraPosisjon' % i, v)
                          v = str(feature.getAttribute('lokasjon.stedfestinger.stedfesting.til_posisjon'))
                          if v != 'None':
                              feature.setAttribute(u'lineærPosisjon{%d}.LineærPosisjonStrekning.tilPosisjon' % i, v)

                          v = str(feature.getAttribute('lokasjon.stedfestinger.stedfesting.sideposisjon'))
                          if v != 'None':
                              feature.setAttribute(u'lineærPosisjon{%d}.LineærPosisjonStrekning.sideposisjon' % i, v)

                          v = str(feature.getAttribute('lokasjon.stedfestinger.stedfesting.retning'))
                          if v != 'None':
                              feature.setAttribute(u'lineærPosisjon{%d}.LineærPosisjonStrekning.retning' % i, v.lower())
                          feature.setAttribute(u'lineærPosisjon{%d}.LineærPosisjonStrekning.lineærReferanseMetode' % i, 'normalisert')

                      else:
                          # Punktstedfesting
                          v = str(feature.getAttribute('lokasjon.stedfestinger.stedfesting.veglenkeid'))
                          if v != 'None':
                              feature.setAttribute(u'lineærPosisjon{%d}.LineærPosisjonPunkt.nettverkselement.xlink_href' % i, 'Veglenke.gml#' + ns + '.rl.' + v)
                              feature.setAttribute(u'lineærPosisjon{%d}.LineærPosisjonPunkt.veglenkeid' % i, v)
                          feature.setAttribute(u'lineærPosisjon{%d}.LineærPosisjonPunkt.lenkesekvens.Identifikasjon.navnerom'  % i, ns + '.rls')
                          feature.setAttribute(u'lineærPosisjon{%d}.LineærPosisjonPunkt.lenkesekvens.Identifikasjon.lokalId'  % i, v)

                          v = str(feature.getAttribute('lokasjon.stedfestinger.stedfesting.posisjon'))
                          if v != 'None':
                              feature.setAttribute(u'lineærPosisjon{%d}.LineærPosisjonPunkt.posisjon' % i, v)

                          v = str(feature.getAttribute(u'lokasjon.stedfestinger.stedfesting.sideposisjon'))
                          if v != 'None':
                              feature.setAttribute(u'lineærPosisjon{%d}.LineærPosisjonPunkt.sideposisjon' % i, v)
                          feature.setAttribute(u'lineærPosisjon{%d}.LineærPosisjonPunkt.lineærReferanseMetode' % i, 'normalisert')

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute(u'lineærPosisjon{%d}.LineærPosisjonStrekning.nettverkselement.xlink_href' % i, 'Veglenke.gml#' + ns + '.rl.' + v)
                          feature.setAttribute(u'lineærPosisjon{%d}.LineærPosisjonStrekning.veglenkeid' % i, v)
                          feature.setAttribute(u'lineærPosisjon{%d}.LineærPosisjonStrekning.lenkesekvens.Identifikasjon.navnerom'  % i, ns + '.rls')
                          feature.setAttribute(u'lineærPosisjon{%d}.LineærPosisjonStrekning.lenkesekvens.Identifikasjon.lokalId'  % i, v)

                      v = str(feature.getAttribute('lokasjon.stedfestinger.stedfesting{%d}.fra_posisjon' % i))
                      if v != 'None':
                          feature.setAttribute(u'lineærPosisjon{%d}.LineærPosisjonStrekning.fraPosisjon' % i, v)

                      v = str(feature.getAttribute('lokasjon.stedfestinger.stedfesting{%d}.til_posisjon' % i))
                      if v != 'None':
                          feature.setAttribute(u'lineærPosisjon{%d}.LineærPosisjonStrekning.tilPosisjon' % i, v)

                      v = str(feature.getAttribute('lokasjon.stedfestinger.stedfesting{%d}.sideposisjon' % i))
                      if v != 'None':
                          feature.setAttribute(u'lineærPosisjon{%d}.LineærPosisjonStrekning.sideposisjon' % i, v)

                      v = str(feature.getAttribute('lokasjon.stedfestinger.stedfesting{%d}.retning' % i))
                      if v != 'None':
                          feature.setAttribute(u'lineærPosisjon{%d}.LineærPosisjonStrekning.retning' % i, v.lower())
                      feature.setAttribute(u'lineærPosisjon{%d}.LineærPosisjonStrekning.lineærReferanseMetode' % i, 'normalisert')

                  else:
                      # Punktstedfesting
                      v = str(feature.getAttribute('lokasjon.stedfestinger.stedfesting{%d}.veglenkeid' % i))
                      if v != 'None':
                          feature.setAttribute(u'lineærPosisjon{%d}.LineærPosisjonPunkt.nettverkselement.xlink_href' % i, 'Veglenke.gml#' + ns + '.rl.' + v)
                          feature.setAttribute(u'lineærPosisjon{%d}.LineærPosisjonPunkt.veglenkeid' % i, v)
                          feature.setAttribute(u'lineærPosisjon{%d}.LineærPosisjonPunkt.lenkesekvens.Identifikasjon.navnerom'  % i, ns + '.rls')
                          feature.setAttribute(u'lineærPosisjon{%d}.LineærPosisjonPunkt.lenkesekvens.Identifikasjon.lokalId'  % i, v)

                      v = str(feature.getAttribute('lokasjon.stedfestinger.stedfesting{%d}.posisjon' % i))
                      if v != 'None':
                          feature.setAttribute(u'lineærPosisjon{%d}.LineærPosisjonPunkt.posisjon' % i, v)

                      v = str(feature.getAttribute('lokasjon.stedfestinger.stedfesting{%d}.sideposisjon' % i))
                      if v != 'None':
                          feature.setAttribute(u'lineærPosisjon{%d}.LineærPosisjonPunkt.sideposisjon' % i, v)
                      feature.setAttribute(u'lineærPosisjon{%d}.LineærPosisjonPunkt.lineærReferanseMetode' % i, 'normalisert')

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  v = str(feature.getAttribute('lokasjon.vegreferanser.vegreferanse{%d}.kategori' % i))
                  if v != 'None':
                      feature.setAttribute('vegreferanse{%d}.Vegreferanse.vegkategori' % i, v)
                      feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> GeometryReplacer
Note: Geometri
GeometryReplacer
    KIND_LONG = OGC Well Known Text
    OGC_WKT_PRECISION_DISPLAY = 64-bit
    REMOVE_ATTRIBUTE = Yes
    SOURCE = @Value(geometri)
    -> CoordinateSystemSetter
    -> CoordinateSystemSetter_2
    -> 3DForcer
3DForcer
    KEEPZVAL = Yes
    ZVALATTR = NaN
    -> CoordinateSystemSetter_3
CoordinateSystemSetter_3
    COORDSYS = EPSG:6173
    -> Deaggregator
CoordinateSystemSetter [off]
    COORDSYS = @Value(epsg)
    -> Deaggregator
CoordinateSystemSetter_2 [off]
    COORDSYS = EPSG:25833
    -> Deaggregator
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Splitter multigeometrier
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NullAttributeMapper
NullAttributeMapper
    ATTRCHOICE = Selected Attributes
    ATTRLIST = _part_number
    NEW_VALUE = 0
    NULL_TREATMENT = New Value
    SOURCE_ATTR_VAL = Null Empty "Missing (Selected Attributes Only)"
    -> StringConcatenator
StringConcatenator
    ACTION = Create New Attribute
    PARM_LINE = @Value(gml_id)_@Value(_part_number)
    VAL_ATTR = gml_id
    -> Output (output)
Output (output)
