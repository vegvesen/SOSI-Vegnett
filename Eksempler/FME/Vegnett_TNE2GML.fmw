FME workspace Vegnett_TNE2GML.fmw

Parameters:
- knr = 403   # Kommunenummer
- detaljNivå = Kjørefelt   # Detaljnivå
- Filename = Vegnettstest.gml
- DestDataset_GML = C:\DATA\GitHub\SOSI-Vegnett\trunk\Eksempler\GML\Vegnettstest.gml   # Destination Geography Markup Language (GML) File
- namespace = vegvesen.no.nvdb   # " " Namespace

Writers:
- GML_1: GML to $(DestDataset_GML)

Note: Id-verdier
AttributeCreator_5
    ATTR_TABLE:
      SET_TO identifikasjon.Identifikasjon.lokalId = @Value(OID)
      SET_TO identifikasjon.Identifikasjon.navnerom = $(namespace).rls
      SET_TO gml_id = $(namespace).rls.@Value(OID)
    -> FeatureMerger [input 1]
Note: Kobler CurveSegment til / RefLinkPart
InlineQuerier
    QUERY_DEF:
      RefLinkPartExtended,SELECT DISTINCT * FROM RefLinkPart
      INNER JOIN CurveSegment ON RefLinkPart.REFLINK_OID = CurveSegment.REFLINK_OID
      WHERE (RefLinkPart.FROM_MEASURE < CurveSegment.TO_MEASURE AND RefLinkPart.TO_MEASURE > CurveSegment.FROM_MEASURE) ,FIRST
    TABLE_DEF = CurveSegment,REFLINK_OID,text,FROM_MEASURE,text,TO_MEASURE,text,RefLinkPart,REFLINK_OID,text,FROM_MEASURE,text,TO_MEASURE,text
    QUERY_SCHEMA = RefLinkPartExtended,REFLINK_OID,text,FROM_MEASURE,text,TO_MEASURE,text,RefLinkPart.fme_feature_content,fme_feature_content,CurveSegment.fme_feature_content,fme_feature_content
    RefLinkPartExtended -> DuplicateRemover
Note: Fjerner duplikater
DuplicateRemover
    KEYATTR = OBJECTID
    UNIQUE -> GeometryPropertySetter_2
Note: Setter geometriegenskap
GeometryPropertySetter_2
    GEOM_NAME_FIELD = senterlinje
    SETTYPE_PARAM = Geometry Name
    OVERWRITE_CHOICE = Yes
    SET -> CoordinateRounder_2
CoordinateRounder_2
    YPREC = 3
    XPREC = 3
    ZPREC = 3
    ROUNDED -> AttributeCreator_2
Note: Id-verdier
AttributeCreator_2
    ATTR_TABLE:
      SET_TO identifikasjon.Identifikasjon.lokalId = @Value(OBJECTID)
      SET_TO identifikasjon.Identifikasjon.navnerom = $(namespace).rlp
      SET_TO gml_id = $(namespace).rl.@Value(OBJECTID)
      SET_TO standardLRM = 2
    -> StringConcatenator_2
    -> StringConcatenator_3
Note: sekvens.xlink_href
StringConcatenator_3
    ACTION = Create New Attribute
    PARM_LINE = $(Filename)#$(namespace).rls.@Value(REFLINK_OID)
    VAL_ATTR = sekvens.xlink_href
    -> PythonCaller
AttributeCreator_8
    ATTR_TABLE = SET_TO ekte = ja
    -> TopologyBuilder [input 1]
Note: Vegreferanse / (Kun rundkjøringer)
FeatureReader_4
    FEATURETYPES_RADIO = FEATURETYPES
    GEODATABASE_SDE_CREDENTIALS_OVERRIDE = NO
    INTERACT = Intersects
    GEODATABASE_SDE_CLIP_TO_ENVELOPE = NO
    FEATURETYPES = SDE_TNE.TNE_FT_Vegreferanse_532_10
    GEODATABASE_SDE_SPLIT_MULTI_PART_ANNOS = no
    GEODATABASE_SDE_FEATURE_READ_MODE = Features
    GEODATABASE_SDE_USE_SEARCH_ENVELOPE = NO
    GEODATABASE_SDE_SEARCH_ORDER = SPATIAL_FIRST
    GEODATABASE_SDE_QUERY_FEATURE_TYPES_FOR_MERGE_FILTERS = Yes
    GEODATABASE_SDE_CONNECTION_FILE = C:\Users\knjetl\AppData\Roaming\ESRI\Desktop10.2\ArcCatalog\PTNE-sde_tne_read@svvkartp.vegvesen.no.sde
    WHERE = TO_DATE = 99991231 AND (HP_4569>= 400 AND HP_4569 <= 599)
    ATTRIBUTES = SDE_TNE.TNE_FT_Vegreferanse_532_10,"OBJECTID,NETOBJECTTV_ID,FROM_DATE,TO_DATE,SEQ_NO,FYNR_4591,KMNR_4592,VKTG_4566,VSOV_4570,VGNR_4568,HP_4569,VSTS_4567,FRMT_4571,TLMT_4572,BRK1_4576,BRK2_4577,VGTP_4574,FVKD_4573,ENRG_4707,SVTP_4575,MDAT_4578,ROUTE_ID,FROM_MEASURE,TO_MEASURE,DIRECTION,TOPOLOGY_LEVEL,SHAPE.LEN"
    GEODATABASE_SDE_CACHE_MULTIPATCH_TEXTURES = yes
    GEODATABASE_SDE_SPLIT_COMPLEX_ANNOS = no
    GEODATABASE_SDE_SEARCH_METHOD = GEODB_INTERSECTS
    ATTR_ACCUM_MODE = Only Use Result
    GEODATABASE_SDE_IGNORE_NETWORK_INFO = yes
    GEODATABASE_SDE_MERGE_FEAT_LINKED_ANNOS = no
    GEODATABASE_SDE_RESOLVE_DOMAINS = no
    GEODATABASE_SDE_PERSISTENT_CONNECTION = no
    GEODATABASE_SDE_TRANSLATE_SPATIAL_DATA_ONLY = no
    GEODATABASE_SDE_CHECK_SIMPLE_GEOM = no
    GEODATABASE_SDE_REMOVE_TABLE_QUALIFIER = NO
    GEODATABASE_SDE_ALIAS_MODE = NONE
    GEODATABASE_SDE_SPLIT_COMPLEX_EDGES = no
    GEODATABASE_SDE_RESOLVE_SUBTYPE_NAMES = yes
    GEODATABASE_SDE_VERSION_OVERRIDE = NO
    SUPPORTED_SPATIAL_INTERACTIONS = ENVELOPE_INTERSECT%INTERSECTS%CONTAINS%CROSSES%DISJOINT%EQUALS%OVERLAPS%TOUCHES%WITHIN
    COMBINE_GEOM = Use Result
    GEODATABASE_SDE_IGNORE_RELATIONSHIP_INFO = yes
    FORMAT = GEODATABASE_SDE
    SDE_TNE.TNE_FT_Vegreferanse_532_10 -> AttributeKeeper_2
Veglenke (writer GML_1)
    attributes: nettverk.nilReason xml_buffer, nettverk.gml_remoteSchema xml_buffer, nettverk.xlink_href xml_buffer, nettverk.owns xml_boolean, standardLRM xml_buffer, måltLengde xml_real64, startposisjon xml_real64, sluttposisjon xml_real64, sekvens.nilReason xml_buffer, sekvens.gml_remoteSchema xml_buffer, sekvens.xlink_href xml_buffer, sekvens.owns xml_boolean, sluttnode.nilReason xml_buffer, sluttnode.gml_remoteSchema xml_buffer, sluttnode.xlink_href xml_buffer, sluttnode.owns xml_boolean, startnode.nilReason xml_buffer, startnode.gml_remoteSchema xml_buffer, startnode.xlink_href xml_buffer, startnode.owns xml_boolean, senterlinje xml_geometry, veglenkeadresse.Veglenkeadresse.kommunenummer xml_buffer, veglenkeadresse.Veglenkeadresse.adressekode xml_int64, veglenkeadresse.Veglenkeadresse.adressenavn xml_buffer, veglenkeadresse.Veglenkeadresse.sideveg xml_boolean, brøytes xml_boolean, detaljnivå xml_buffer, feltoversikt xml_buffer, trafikkreguleringer xml_buffer, konnekteringslenke xml_boolean,
      typeVeg xml_buffer, veglenkeFraDato xml_date, veglenkeTilDato xml_date, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer
Veglenkesett (writer GML_1) [off]
    attributes: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

Bookmark: Kommune
Creator_2
    NUM = 1
    GEOMTYPE = Geometry Object
    CREATED -> AttributeCreator_3
Note: Nettverk-id
AttributeCreator_3
    ATTR_TABLE = SET_TO _nettverk_id = $(namespace).nv.$(knr)
    -> AttributeRenamer
    -> StringConcatenator_6
StringConcatenator_6
    ACTION = Create New Attribute
    PARM_LINE = KOMM=$(knr)
    VAL_ATTR = _kommunewhere
    -> StringConcatenator
StringConcatenator
    ACTION = Create New Attribute
    PARM_LINE = $(Filename)#@Value(_nettverk_id)
    VAL_ATTR = nettverk.xlink_href
    -> FeatureReader
FeatureReader
    FEATURETYPES_RADIO = FEATURETYPES
    OUTPUT_FEATURES_DISPLAY = Based on Connections
    INTERACT = <No Spatial Filter>
    FEATURETYPES = N250_AdminFlate
    WHERE = @Value(_kommunewhere)
    ATTRIBUTES = N250_AdminFlate,"OBJECTID,OBJTYPE,NAVN,KOMM,OPPDATERINGSDATO,Shape_Length,Shape_Area",N250_AdminGrense,"OBJECTID,OBJTYPE,OPPDATERINGSDATO,Shape_Length",N250_AdminGrensePunkt,"OBJECTID,OBJTYPE,GRENSEPUNKTTYPE,GRENSEPUNKTNUMMER,GRUNNLINJENUMMER,NAVN,OPPDATERINGSDATO",N250_AnleggsLinje,"OBJECTID,OBJTYPE,OPPDATERINGSDATO,Shape_Length",N250_AnleggsPunkt,"OBJECTID,OBJTYPE,FYRLISTENUMMER,OPPDATERINGSDATO",N250_ArealdekkeFlate,"OBJECTID,OBJTYPE,VANNBR,HOYDE,VATNLNR,OPPDATERINGSDATO,Shape_Length,Shape_Area",N250_ArealdekkePunkt,"OBJECTID,OBJTYPE,NAVN,OPPDATERINGSDATO",N250_Bane,"OBJECTID,OBJTYPE,JERNBANETYPE,SPORANTALL,MEDIUM,OPPDATERINGSDATO,Shape_Length",N250_BegrensningsKurve,"OBJECTID,OBJTYPE,OPPDATERINGSDATO,Shape_Length",N250_BygningsPunkt,"OBJECTID,OBJTYPE,BYGGKAT,OPPDATERINGSDATO",N250_ElvBekk,"OBJECTID,OBJTYPE,VANNBR,OPPDATERINGSDATO,Shape_Length",N250_Ferge,"OBJECTID,OBJTYPE,VEGKATEGORI,VEGNUMMER,OPPDATERINGSDATO,Shape_Length",N250_Grunnlinje,"OBJECTID,OBJTYPE,OPPDATERINGSDATO,Shape_Length",N250_HoydeKontur,"OBJECTID,OBJTYPE,HOYDE,OPPDATERINGSDATO,MEDIUM,Shape_Length",N250_HoydeLag,"OBJECTID,OBJTYPE,MINHOYDE,MAKSHOYDE,OPPDATERINGSDATO,Shape_Length,Shape_Area",N250_HoydePunkt,"OBJECTID,OBJTYPE,HOYDE,OPPDATERINGSDATO",N250_Hoydetall,"OBJECTID,FeatureID,ZOrder,AnnotationClassID,SymbolID,Status,TextString,FontName,FontSize,Bold,Italic,Underline,VerticalAlignment,HorizontalAlignment,XOffset,YOffset,Angle,FontLeading,WordSpacing,CharacterWidth,CharacterSpacing,FlipAngle,Override,TEKSTT_,TEKS_ID,OBJTYPE,NAVNTYPE,SKRIFTKODE,SPERRING,TRNORD,TROST,SNAVN,SSR_ID,STRENG,ID,SYMBOL,LEVEL_,FRISPERR,OPPDATERINGSDATO,Shape_Length,Shape_Area,OBJEKT_X,OBJEKT_Y",N250_JernbaneStasjon,"OBJECTID,OBJTYPE,NAVN,STASJONSFORMAL,OPPDATERINGSDATO",N250_LufthavnPunkt,"OBJECTID,OBJTYPE,ICAO_KODE,IATA_KODE,LUFTHAVNTYPE,TRAFIKKTYPE,NAVN,EIER,OPPDATERINGSDATO",N250_Navn,"OBJECTID,FeatureID,ZOrder,AnnotationClassID,SymbolID,Status,TextString,FontName,FontSize,Bold,Italic,Underline,VerticalAlignment,HorizontalAlignment,XOffset,YOffset,Angle,FontLeading,WordSpacing,CharacterWidth,CharacterSpacing,FlipAngle,Override,TEKST_,TEKST_ID,OBJTYPE,NAVNTYPE,SKRIFTKODE,SPERRING,TRNORD,TROST,SNAVN,SSR_ID,STRENG,ID,SYMBOL,LEVEL_,FRISPERR,OPPDATERINGSDATO,Shape_Length,Shape_Area,OBJEKT_X,OBJEKT_Y",N250_TettSted,"OBJECTID,OBJTYPE,TSTED,OPPDATERINGSDATO",N250_TuristHytte,"OBJECTID,OBJTYPE,NAVN,BETJENINGSGRAD,HYTTEEIER,OPPDATERINGSDATO,BYGGKAT",N250_VegSti,"OBJECTID,OBJTYPE,VEGKATEGORI,VEGNUMMER,VEGSTATUS,MOTORVEGTYPE,MEDIUM,RUTEMERKING,OPPDATERINGSDATO,Shape_Length",N250_VerneOmrade,"OBJECTID,OBJTYPE,NAVN,VERNEFORM,OPPDATERINGSDATO,VERNEDATO,Shape_Length,Shape_Area"
    DATASET = K:\Vektor\00\23-N250\00\EsriGDB\N250.gdb
    ATTR_ACCUM_MODE = Merge Initiator and Result
    ATTR_CONFLICT_RES = Use Result
    SUPPORTED_SPATIAL_INTERACTIONS = ENVELOPE_INTERSECT%INTERSECTS%CONTAINS%CROSSES%DISJOINT%EQUALS%OVERLAPS%TOUCHES%WITHIN
    COMBINE_GEOM = Use Result
    FORMAT = GEODATABASE_FILE
    N250_AdminFlate -> Dissolver
Dissolver
    ACCUM_INPUT_ATTRS = No
    GROUP_BY = KOMM nettverk.xlink_href
    CONNECT_Z_MODE = First Wins
    NO_OVRLP = No
    AREA -> DonutHoleExtractor
DonutHoleExtractor
    OUTERSHELL -> FeatureReader_2
    OUTERSHELL -> FeatureReader_3
    OUTERSHELL -> FeatureReader_4
Note: Reflink
FeatureReader_3
    FEATURETYPES_RADIO = FEATURETYPES
    GEODATABASE_SDE_CREDENTIALS_OVERRIDE = NO
    OUTPUT_FEATURES_DISPLAY = Based on Connections
    INTERACT = Intersects
    GEODATABASE_SDE_CLIP_TO_ENVELOPE = NO
    FEATURETYPES = SDE_TNE.TNE_RefLink
    GEODATABASE_SDE_SPLIT_MULTI_PART_ANNOS = no
    GEODATABASE_SDE_FEATURE_READ_MODE = Features
    GEODATABASE_SDE_USE_SEARCH_ENVELOPE = NO
    GEODATABASE_SDE_CONNECTION_FILE = C:\Users\knjetl\AppData\Roaming\ESRI\Desktop10.2\ArcCatalog\PTNE-sde_tne_read@svvkartp.vegvesen.no.sde
    ATTRIBUTES = SDE_TNE.TNE_RefLink,"OBJECTID,OID,VID,REFOBJ_TYPE,NEXT_FREE_PORT_NUMBER,LENGTH,FIXED_LENGTH,SHAPE.LEN"
    GEODATABASE_SDE_CACHE_MULTIPATCH_TEXTURES = no
    GEODATABASE_SDE_SPLIT_COMPLEX_ANNOS = no
    ATTR_ACCUM_MODE = Merge Initiator and Result
    GEODATABASE_SDE_IGNORE_NETWORK_INFO = no
    GEODATABASE_SDE_MERGE_FEAT_LINKED_ANNOS = no
    GEODATABASE_SDE_RESOLVE_DOMAINS = no
    ATTR_CONFLICT_RES = Use Result
    GEODATABASE_SDE_PERSISTENT_CONNECTION = no
    GEODATABASE_SDE_TRANSLATE_SPATIAL_DATA_ONLY = no
    GEODATABASE_SDE_CHECK_SIMPLE_GEOM = no
    GEODATABASE_SDE_REMOVE_TABLE_QUALIFIER = NO
    GEODATABASE_SDE_ALIAS_MODE = NONE
    GEODATABASE_SDE_RESOLVE_SUBTYPE_NAMES = no
    GEODATABASE_SDE_SPLIT_COMPLEX_EDGES = no
    GEODATABASE_SDE_VERSION_OVERRIDE = NO
    SUPPORTED_SPATIAL_INTERACTIONS = ENVELOPE_INTERSECT%INTERSECTS%CONTAINS%CROSSES%DISJOINT%EQUALS%OVERLAPS%TOUCHES%WITHIN
    COMBINE_GEOM = Use Result
    GEODATABASE_SDE_IGNORE_RELATIONSHIP_INFO = no
    FORMAT = GEODATABASE_SDE
    SDE_TNE.TNE_RefLink -> AttributeCreator_5
Note: CurveSegment, RefLinkPart og RefNode
FeatureReader_2
    FEATURETYPES_RADIO = FEATURETYPES
    GEODATABASE_SDE_CREDENTIALS_OVERRIDE = NO
    OUTPUT_FEATURES_DISPLAY = Based on Connections
    INTERACT = Intersects
    GEODATABASE_SDE_CLIP_TO_ENVELOPE = NO
    FEATURETYPES = SDE_TNE.TNE_CurveSegment SDE_TNE.TNE_RefLinkPart SDE_TNE.TNE_RefNode
    GEODATABASE_SDE_SPLIT_MULTI_PART_ANNOS = no
    GEODATABASE_SDE_FEATURE_READ_MODE = Features
    GEODATABASE_SDE_USE_SEARCH_ENVELOPE = NO
    GEODATABASE_SDE_CONNECTION_FILE = C:\Users\knjetl\AppData\Roaming\ESRI\Desktop10.2\ArcCatalog\PTNE-sde_tne_read@svvkartp.vegvesen.no.sde
    WHERE = TO_DATE = 99991231
    ATTRIBUTES = SDE_TNE.TNE_CurveSegment,"OBJECTID,REFLINK_OID,FROM_DATE,TO_DATE,FROM_MEASURE,TO_MEASURE,SEG_DATE,LENGTH,CLASS_CODE,OBJECT_CODE,MEDIUM,QUALITY_METHOD,QUALITY_ACCURACY,QUALITY_VISIBILITY,QUALITY_METHOD_HEIGHT,QUALITY_ACCURACY_HEIGHT,QUALITY_TOLERANCE,MUNICIPALITY,SHAPE.LEN",SDE_TNE.TNE_RefLinkPart,"OBJECTID,REFLINK_OID,FROM_DATE,TO_DATE,FROM_MEASURE,TO_MEASURE,FROM_REFNODE_OID,TO_REFNODE_OID,LENGTH,TOPOLOGY_LEVEL,SUPER_OID,SUPER_FROM_MEASURE,SUPER_TO_MEASURE,LANE,DIRECTION,SHAPE.LEN",SDE_TNE.TNE_RefNode,"OBJECTID,OID,VID,REFOBJ_TYPE,NEXT_FREE_PORT_NUMBER,FROM_DATE,TO_DATE"
    GEODATABASE_SDE_CACHE_MULTIPATCH_TEXTURES = no
    GEODATABASE_SDE_SPLIT_COMPLEX_ANNOS = no
    ATTR_ACCUM_MODE = Merge Initiator and Result
    GEODATABASE_SDE_IGNORE_NETWORK_INFO = no
    GEODATABASE_SDE_MERGE_FEAT_LINKED_ANNOS = no
    GEODATABASE_SDE_RESOLVE_DOMAINS = no
    ATTR_CONFLICT_RES = Use Result
    GEODATABASE_SDE_PERSISTENT_CONNECTION = no
    GEODATABASE_SDE_TRANSLATE_SPATIAL_DATA_ONLY = no
    GEODATABASE_SDE_CHECK_SIMPLE_GEOM = no
    GEODATABASE_SDE_REMOVE_TABLE_QUALIFIER = NO
    GEODATABASE_SDE_ALIAS_MODE = NONE
    GEODATABASE_SDE_RESOLVE_SUBTYPE_NAMES = no
    GEODATABASE_SDE_SPLIT_COMPLEX_EDGES = no
    GEODATABASE_SDE_VERSION_OVERRIDE = NO
    SUPPORTED_SPATIAL_INTERACTIONS = ENVELOPE_INTERSECT%INTERSECTS%CONTAINS%CROSSES%DISJOINT%EQUALS%OVERLAPS%TOUCHES%WITHIN
    COMBINE_GEOM = Use Result
    GEODATABASE_SDE_IGNORE_RELATIONSHIP_INFO = no
    FORMAT = GEODATABASE_SDE
    SDE_TNE.TNE_RefLinkPart -> PythonCaller_3
    SDE_TNE.TNE_CurveSegment -> InlineQuerier [input 1]
    SDE_TNE.TNE_RefNode -> AttributeCreator_8

Bookmark: Nettverk
AttributeRenamer
    ATTR_TABLE = RENAME_SET_DEFAULT _nettverk_id > gml_id
    -> Nettverk (writer GML_1)
Nettverk (writer GML_1)
    attributes: nettverkselement{}.nilReason xml_buffer, nettverkselement{}.gml_remoteSchema xml_buffer, nettverkselement{}.xlink_href xml_buffer, nettverkselement{}.owns xml_boolean, nettverksnavn xml_buffer

Bookmark: Detaljnivå
Note: Finner valgt detaljnivå
PythonCaller_3
    NEW_ATTRIBUTES = _topoWhere
    PYTHONSOURCE:
      import fmeobjects

      def topolevel(feature):
          par = '0,1,2,3'
          if FME_MacroValues['detaljNivå'] == 'Vegtrase':
              par = '0,1'
          elif FME_MacroValues['detaljNivå'] == 'Kjørebane':
              par = '1,2'
          elif FME_MacroValues['detaljNivå'] == 'Kjørefelt':
              par = '1,2,3'
          feature.setAttribute("_topoWhere", par)
    PYTHONSYMBOL = topolevel
    -> TestFilter_4
Note: Finner lenker som skal være med
TestFilter_4
    TEST_LIST = BOOL_OP,OR,COMPOSITE_TEST,<Unused>,TEST_CLAUSE,"TEST @Value(TOPOLOGY_LEVEL) IN @Value(_topoWhere)",TOPOLEVEL
    DEFAULT_VALUE = <UNFILTERED>
    TOPOLEVEL -> InlineQuerier [input 2]

Bookmark: Veglenkesekvens
StringConcatenator_2
    ACTION = Create New Attribute
    PARM_LINE = $(Filename)#@Value(gml_id)
    VAL_ATTR = xlink_href
    -> AttributeKeeper
AttributeKeeper
    KEEP_ATTRS = REFLINK_OID,xlink_href
    -> FeatureMerger [input 2]
FeatureMerger
    LIST_NAME = sekvensdel
    SUPPLIERS_FIRST = No
    JOIN_KEYS = @Value(OID) @Value(REFLINK_OID) AUTO
    IGNORE_NULLS = No
    ATTR_ACCUM_MODE = Merge Supplier
    GEOM_TYPE = Build Polygons
    PROCESS_DUPS = Yes
    ATTR_CONFLICT_RES = Use Requestor
    CONNECT_Z_MODE = First Wins
    MERGE_TYPE = Attributes Only
    MERGED -> Veglenkesekvens (writer GML_1)
Veglenkesekvens (writer GML_1)
    attributes: nettverk.nilReason xml_buffer, nettverk.gml_remoteSchema xml_buffer, nettverk.xlink_href xml_buffer, nettverk.owns xml_boolean, standardLRM xml_buffer, måltLengde xml_real64, sekvensdel{}.nilReason xml_buffer, sekvensdel{}.gml_remoteSchema xml_buffer, sekvensdel{}.xlink_href xml_buffer, sekvensdel{}.owns xml_boolean, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer

Bookmark: Døper om og mapper egenskaper
Note: Ordner nullverdier for kvalitetsattributter
PythonCaller
    PYTHONSOURCE:
      import fmeobjects
      # Template Function interface:
      def processFeature(feature):
          par=feature.getAttribute('QUALITY_METHOD')
          if par == -1 or par == 0:
              feature.removeAttribute('QUALITY_METHOD')
          par=feature.getAttribute('QUALITY_ACCURACY')
          if par == -1 or par == 0:
              feature.removeAttribute('QUALITY_ACCURACY')
          par=feature.getAttribute('QUALITY_METHOD_HEIGHT')
          if par == -1 or par == 0:
              feature.removeAttribute('QUALITY_METHOD_HEIGHT')
          par=feature.getAttribute('QUALITY_ACCURACY_HEIGHT')
          if par == -1 or par == 0:
              feature.removeAttribute('QUALITY_ACCURACY_HEIGHT')
    PYTHONSYMBOL = processFeature
    -> AttributeRenamer_2
AttributeRenamer_2
    ATTR_LIST = QUALITY_METHOD,kvalitet.Posisjonskvalitet.målemetode,"",QUALITY_ACCURACY,kvalitet.Posisjonskvalitet.nøyaktighet,"",QUALITY_METHOD_HEIGHT,kvalitet.Posisjonskvalitet.målemetodeHøyde,"",QUALITY_ACCURACY_HEIGHT,kvalitet.Posisjonskvalitet.nøyaktighetHøyde,"",KOMM,kommunenummer,"",FROM_DATE,veglenkeFraDato,"",TO_DATE,veglenkeTilDato,""
    -> StringFormatter
StringFormatter
    FORMAT = 04s
    SRC_ATTRS = kommunenummer
    -> AttributeValueMapper_3
Note: medium
AttributeValueMapper_3
    SRC = MEDIUM
    DIRECTION = Forward (Source To Destination)
    LUT = 0,T,1,B,2,L,3,U
    VAL_ATTR = medium
    DEFAULT_VALUE = T
    -> AttributeCopier
Note: lenkeposisjoner
AttributeCopier
    ATTR_LIST = FROM_MEASURE,startposisjon,"",TO_MEASURE,sluttposisjon,""
    -> AttributeValueMapper
    -> AttributeValueMapper_2
Note: konnekteringslenke / NB! Må løeses på andre måter nå, ligger i vegnettsmodellen
AttributeValueMapper [off]
    SRC = CLASS_CODE
    DIRECTION = Forward (Source To Destination)
    LUT = 7004,true
    VAL_ATTR = konnekteringslenke
    DEFAULT_VALUE = false
    -> AttributeValueMapper_2
Note: detaljnivå
AttributeValueMapper_2
    SRC = TOPOLOGY_LEVEL
    DIRECTION = Forward (Source To Destination)
    LUT = 0,Vegtrase,2,Kjørebane,3,Kjørefelt
    VAL_ATTR = detaljnivå
    DEFAULT_VALUE = FME_NULL_VALUE
    -> DateFormatter
DateFormatter
    SRCFMT = Unknown - Automatic Detection
    INVALID_DATE_VALUE = _FME_NO_OP_
    FMT = ISO Date (%Y-%m-%d)
    DATE_ATTR = veglenkeFraDato,veglenkeTilDato
    -> TestFilter_2

Bookmark: Overodnet lenke for objekttypene Svingekonnekteringslenke og Kjørefelt
Note: Skiller ut / Svingekonnekteringslenker / og Kjørefeltlenker
TestFilter_2
    TEST_LIST = BOOL_OP,OR,COMPOSITE_TEST,<Unused>,TEST_CLAUSE,"TEST @Value(CLASS_CODE) = 7004",Svingekonnekteringslenke,BOOL_OP,OR,COMPOSITE_TEST,<Unused>,TEST_CLAUSE,"TEST @Value(CLASS_CODE) = 7010",Kjørefelt
    DEFAULT_VALUE = <UNFILTERED>
    Svingekonnekteringslenke -> BulkAttributeRenamer_2
    Kjørefelt -> BulkAttributeRenamer_2
    <UNFILTERED> -> InlineQuerier_2 [input 2]
    <UNFILTERED> -> AttributeValueMapper_4
BulkAttributeRenamer_2
    ATTRLIST = CLASS_CODE
    PATTERN_ACTION_DISP = Add String Prefix
    ATTRCHOICE = Selected Attributes
    REPLACE_STR = FLD
    -> InlineQuerier_2 [input 1]
Note: Koblertil overodnet lenke
InlineQuerier_2
    QUERY_DEF:
      Ut,SELECT DISTINCT Kjørefelt.*, Andre.CLASS_CODE FROM Kjørefelt
      INNER JOIN Andre ON Kjørefelt.SUPER_OID = Andre.REFLINK_OID
      WHERE (Kjørefelt.SUPER_FROM_MEASURE < Andre.TO_MEASURE AND Kjørefelt.SUPER_TO_MEASURE > Andre.FROM_MEASURE) ,FIRST
    TABLE_DEF = Kjørefelt,SUPER_OID,text,SUPER_FROM_MEASURE,text,SUPER_TO_MEASURE,text,OBJECTID,text,Andre,REFLINK_OID,text,FROM_MEASURE,text,TO_MEASURE,text,CLASS_CODE,text
    QUERY_SCHEMA = Ut,SUPER_OID,text,SUPER_FROM_MEASURE,text,SUPER_TO_MEASURE,text,OBJECTID,text,Kjørefelt.fme_feature_content,fme_feature_content,CLASS_CODE,text
    Ut -> DuplicateRemover_2
Note: Fjerner duplikater
DuplicateRemover_2
    KEYATTR = OBJECTID
    UNIQUE -> AttributeValueMapper_4

Bookmark: Type veg for alle lenker, med spesialhåndtering av rundkjøringer
Note: Mapping fra objekttype til typeVeg
AttributeValueMapper_4
    SRC = CLASS_CODE
    DIRECTION = Forward (Source To Destination)
    LUT = 7001,Enkel bilveg,7012,Kanalisert veg,7011,Kanalisert veg,7201,Bilferje,7042,Gang- og sykkelveg,7046,Fortau,6304,Trapp
    VAL_ATTR = typeVeg
    DEFAULT_VALUE = Enkel bilveg
    -> InlineQuerier_3 [input 1]
AttributeKeeper_2
    KEEP_ATTRS = HP_4569,ROUTE_ID,FROM_MEASURE,TO_MEASURE
    -> InlineQuerier_3 [input 2]
Note: Kobler til Vegreferanse / for å identifisere rundkjøringer
InlineQuerier_3
    QUERY_DEF:
      RefLinkPart,SELECT *
      FROM RefLinkPart,FIRST,Rundkjøringer,SELECT DISTINCT RefLinkPart.* FROM RefLinkPart
      INNER JOIN Vegreferanse ON RefLinkPart.REFLINK_OID = Vegreferanse.ROUTE_ID
      WHERE (RefLinkPart.FROM_MEASURE < Vegreferanse.TO_MEASURE AND RefLinkPart.TO_MEASURE > Vegreferanse.FROM_MEASURE) ,FIRST
    TABLE_DEF = RefLinkPart,REFLINK_OID,text,FROM_MEASURE,text,TO_MEASURE,text,CLASS_CODE,text,Vegreferanse,ROUTE_ID,text,FROM_MEASURE,text,TO_MEASURE,text,HP_4569,text
    QUERY_SCHEMA = RefLinkPart,REFLINK_OID,text,FROM_MEASURE,text,TO_MEASURE,text,CLASS_CODE,text,RefLinkPart.fme_feature_content,fme_feature_content,Rundkjøringer,REFLINK_OID,text,FROM_MEASURE,text,TO_MEASURE,text,CLASS_CODE,text,RefLinkPart.fme_feature_content,fme_feature_content
    RefLinkPart -> FeatureMerger_2 [input 1]
    Rundkjøringer -> DuplicateRemover_3
Note: Fjerner duplikater
DuplicateRemover_3
    KEYATTR = OBJECTID
    UNIQUE -> FeatureMerger_2 [input 2]
Note: Finner lenker som er rundkjøring
FeatureMerger_2
    SUPPLIERS_FIRST = No
    JOIN_KEYS = @Value(OBJECTID) @Value(OBJECTID) AUTO
    IGNORE_NULLS = Yes
    MERGE_TYPE = Attributes Only
    SUPPLIER_PREFIX_DUMMY = YES
    PROCESS_DUPS = No
    NOT_MERGED -> NullAttributeMapper
    MERGED -> AttributeCreator_4
Note: typeVeg=Rundkjøring
AttributeCreator_4
    ATTR_LIST = typeVeg,Rundkjøring
    -> NullAttributeMapper
NullAttributeMapper
    SOURCE_ATTR_VAL = Null Empty
    OTHER_VALUE = 0
    ATTRLIST = kvalitet.Posisjonskvalitet.nøyaktighet kvalitet.Posisjonskvalitet.nøyaktighetHøyde detaljnivå kvalitet.Posisjonskvalitet.målemetode kvalitet.Posisjonskvalitet.målemetodeHøyde
    ATTRCHOICE = Selected Attributes
    NULL_TREATMENT = Missing
    -> TopologyBuilder [input 2]

Bookmark: Topologibygging med etablering av manglende noder
Note: Bygger topologi: / Lager manglende noder og finner sammenhenger mellom lenker og noder
TopologyBuilder
    CLEAN_DATA = Yes
    PROP_ATTRS = No
    ALLOW_CYCLES = No
    BOUNDING_EDGES = All
    MAX = 0
    OVERLAPPING_MODE = No
    LINE -> FeatureMerger_3 [input 1]
    NODE -> TestFilter
Note: Identifiserer nye noder / (Pseudonoder)
TestFilter
    TEST_LIST = BOOL_OP,OR,COMPOSITE_TEST,<Unused>,TEST_CLAUSE,"TEST ekte ATTRIBUTE_IS_MISSING """"",PseudoNode
    DEFAULT_VALUE = EksisterendeNode
    EksisterendeNode -> AttributeCreator_7
    PseudoNode -> AttributeCreator_6
Note: OID for nye noder
AttributeCreator_6
    ATTR_LIST = OID,p@Value(_node_number)
    -> AttributeCreator_7
Note: Id-verdier
AttributeCreator_7
    ATTR_TABLE:
      SET_TO identifikasjon.Identifikasjon.lokalId = @Value(OID)
      SET_TO identifikasjon.Identifikasjon.navnerom = $(namespace).rn
      SET_TO gml_id = $(namespace).rn.@Value(OID)
    -> AttributeKeeper_3
    -> ListElementCounter
ListElementCounter
    CNT_ATTR = _element_count
    LIST_NAME = _node_angle{}
    -> TestFilter_3
TestFilter_3
    TEST_LIST = BOOL_OP,OR,COMPOSITE_TEST,<Unused>,TEST_CLAUSE,"TEST @Value(_element_count) >= 1",Aktivenoder
    DEFAULT_VALUE = <UNFILTERED>
    Aktivenoder -> ListExploder
    Aktivenoder -> FeatureMerger_6 [input 1]
AttributeKeeper_3
    KEEP_ATTRS = gml_id,_node_number,identifikasjon.Identifikasjon.lokalId,identifikasjon.Identifikasjon.navnerom
    -> FeatureMerger_3 [input 2]
    -> FeatureMerger_4 [input 2]
Note: Kobler til franode
FeatureMerger_3
    SUPPLIERS_FIRST = No
    JOIN_KEYS = @Value(_from_node) @Value(_node_number) AUTO
    IGNORE_NULLS = Yes
    MERGE_TYPE = Attributes Only
    SUPPLIER_PREFIX_DUMMY = YES
    SUPPLIER_PREFIX = _from_
    PROCESS_DUPS = No
    MERGED -> FeatureMerger_4 [input 1]
    NOT_MERGED -> FeatureMerger_4 [input 1]
Note: Kobler til tilnode
FeatureMerger_4
    SUPPLIERS_FIRST = No
    JOIN_KEYS = @Value(_to_node) @Value(_node_number) AUTO
    IGNORE_NULLS = Yes
    MERGE_TYPE = Attributes Only
    SUPPLIER_PREFIX_DUMMY = YES
    SUPPLIER_PREFIX = _to_
    PROCESS_DUPS = No
    MERGED -> AttributeCreator
    NOT_MERGED -> AttributeCreator
Note: xlink_href / til noder
AttributeCreator
    ATTR_TABLE:
      SET_TO startnode.xlink_href = $(Filename)#@Value(_from_gml_id)
      SET_TO sluttnode.xlink_href = $(Filename)#@Value(_to_gml_id)
    -> Veglenke (writer GML_1)
    -> FeatureMerger_5 [input 2]

Bookmark: Vegnode
ListExploder
    INDEX_ATTR = _element_index
    ATTR_ACCUM_MODE = Merge Incoming List
    ATTR_CONFLICT_RES = Use Original
    LIST_ATTR = _node_angle{}
    ELEMENTS -> AttributeCreator_9
AttributeCreator_9
    ATTR_TABLE = SET_TO _abs_arc_id = @abs(@Value(fme_arc_id))
    -> FeatureMerger_5 [input 1]
Note: Lenker som tilhører nodene
FeatureMerger_5
    SUPPLIERS_FIRST = No
    JOIN_KEYS = @Value(_abs_arc_id) @Value(_arc_id) AUTO
    IGNORE_NULLS = No
    ATTR_ACCUM_MODE = Prefix Supplier
    PROCESS_DUPS = No
    SUPPLIER_PREFIX = arc_
    MERGE_TYPE = Attributes Only
    MERGED -> AttributeCreator_10
Note: xlink_href / til lenker
AttributeCreator_10
    ATTR_TABLE = SET_TO xlink_href = $(Filename)#@Value(arc_gml_id)
    -> TestFilter_5
TestFilter_5
    TEST_LIST = BOOL_OP,OR,COMPOSITE_TEST,<Unused>,TEST_CLAUSE,"TEST @Value(fme_arc_id) > 0",startnodeFor
    DEFAULT_VALUE = sluttnodeFor
    startnodeFor -> FeatureMerger_6 [input 2]
    sluttnodeFor -> FeatureMerger_7 [input 2]
Note: xlink_href for lenker som noden er start for
FeatureMerger_6
    LIST_NAME = startnodeFor
    SUPPLIERS_FIRST = No
    JOIN_KEYS = @Value(_node_number) @Value(_node_number) AUTO
    IGNORE_NULLS = No
    ATTR_ACCUM_MODE = Merge Supplier
    GEOM_TYPE = Build Polygons
    PROCESS_DUPS = Yes
    ATTR_CONFLICT_RES = Use Requestor
    CONNECT_Z_MODE = First Wins
    MERGE_TYPE = Attributes Only
    MERGED -> FeatureMerger_7 [input 1]
    NOT_MERGED -> FeatureMerger_7 [input 1]
Note: xlink_href for lenker som noden er slutt for
FeatureMerger_7
    LIST_NAME = sluttnodeFor
    SUPPLIERS_FIRST = No
    JOIN_KEYS = @Value(_node_number) @Value(_node_number) AUTO
    IGNORE_NULLS = No
    ATTR_ACCUM_MODE = Merge Supplier
    GEOM_TYPE = Build Polygons
    PROCESS_DUPS = Yes
    ATTR_CONFLICT_RES = Use Requestor
    CONNECT_Z_MODE = First Wins
    MERGE_TYPE = Attributes Only
    MERGED -> 2DForcer
    NOT_MERGED -> 2DForcer
2DForcer
    2D -> CoordinateRounder
CoordinateRounder
    YPREC = 3
    XPREC = 3
    ZPREC = 3
    ROUNDED -> GeometryPropertySetter
Note: Setter geometriegenskap
GeometryPropertySetter
    GEOM_NAME_FIELD = posisjon
    SETTYPE_PARAM = Geometry Name
    OVERWRITE_CHOICE = Yes
    SET -> Vegnode (writer GML_1)
Vegnode (writer GML_1)
    attributes: sluttnodeFor{}.nilReason xml_buffer, sluttnodeFor{}.gml_remoteSchema xml_buffer, sluttnodeFor{}.xlink_href xml_buffer, sluttnodeFor{}.owns xml_boolean, startnodeFor{}.nilReason xml_buffer, startnodeFor{}.gml_remoteSchema xml_buffer, startnodeFor{}.xlink_href xml_buffer, startnodeFor{}.owns xml_boolean, posisjon xml_geometry, identifikasjon.Identifikasjon.lokalId xml_buffer, identifikasjon.Identifikasjon.navnerom xml_buffer, identifikasjon.Identifikasjon.versjonId xml_buffer, nettverk.nilReason xml_buffer, nettverk.gml_remoteSchema xml_buffer, nettverk.xlink_href xml_buffer, nettverk.owns xml_boolean, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer
