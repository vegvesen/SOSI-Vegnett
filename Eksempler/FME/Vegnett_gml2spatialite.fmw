FME workspace Vegnett_gml2spatialite.fmw

Parameters:
- SourceDataset_GML_3 = C:\DATA\GitHub\SOSI-Vegnett\trunk\Eksempler\GML\Vegnettstest.gml   # Source Geography Markup Language (GML) File(s)
- DestDataset_SPATIALITE_2 = C:\DATA\GitHub\SOSI-Vegnett\trunk\Eksempler\GML\Vegnettstest.db   # Destination SpatiaLite Database File

Readers:
- GML_1: GML from $(SourceDataset_GML_3)

Writers:
- SPATIALITE_1: SPATIALITE to $(DestDataset_SPATIALITE_2)

Nettverk (reader GML_1)
    attributes: nettverksnavn xml_buffer, nettverkselement{}.nilReason xml_buffer, nettverkselement{}.gml_remoteSchema xml_buffer, nettverkselement{}.xlink_href xml_buffer, nettverkselement{}.owns xml_boolean
    -> nettverk (writer SPATIALITE_1)
nettverk (writer SPATIALITE_1)
    attributes: gml_id string(255), nettverksnavn string(255)
Vegnode (reader GML_1)
    attributes: endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, identifikasjon.Identifikasjon.lokalId xml_buffer, identifikasjon.Identifikasjon.navnerom xml_buffer, identifikasjon.Identifikasjon.versjonId xml_buffer, nettverk.nilReason xml_buffer, nettverk.gml_remoteSchema xml_buffer, nettverk.xlink_href xml_buffer, nettverk.owns xml_boolean, sluttnodeFor{}.nilReason xml_buffer, sluttnodeFor{}.gml_remoteSchema xml_buffer, sluttnodeFor{}.xlink_href xml_buffer, sluttnodeFor{}.owns xml_boolean, startnodeFor{}.nilReason xml_buffer, startnodeFor{}.gml_remoteSchema xml_buffer, startnodeFor{}.xlink_href xml_buffer, startnodeFor{}.owns xml_boolean, posisjon xml_geometry
    -> vegnode (writer SPATIALITE_1)
vegnode (writer SPATIALITE_1)
    attributes: gml_id string(255), kommunenummer string(255), sideposisjon string(255), identifikasjon_identifikasjon_lokalid string(255), identifikasjon_identifikasjon_navnerom string(255), identifikasjon_identifikasjon_versjonid string(255), nettverk_xlink_href string(255), posisjon string(255)
Veglenkesett (reader GML_1)
    attributes: endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, identifikasjon.Identifikasjon.lokalId xml_buffer, identifikasjon.Identifikasjon.navnerom xml_buffer, identifikasjon.Identifikasjon.versjonId xml_buffer, nettverk.nilReason xml_buffer, nettverk.gml_remoteSchema xml_buffer, nettverk.xlink_href xml_buffer, nettverk.owns xml_boolean, navn xml_buffer, lenke{}.nilReason xml_buffer, lenke{}.gml_remoteSchema xml_buffer, lenke{}.xlink_href xml_buffer, lenke{}.owns xml_boolean
    -> veglenkesett (writer SPATIALITE_1)
veglenkesett (writer SPATIALITE_1) [off]
    attributes: gml_parent_id string(255), gml_parent_property string(255), gml_id string(255), endringsflagg_endringsflagg_typeendring string(255), endringsflagg_endringsflagg_tidspunktendring string(255), datafangstdato string(255), oppdateringsdato string(255), kvalitet_posisjonskvalitet_målemetode string(255), kvalitet_posisjonskvalitet_nøyaktighet real(20,0), kvalitet_posisjonskvalitet_synbarhet string(255), kvalitet_posisjonskvalitet_målemetodehøyde string(255), kvalitet_posisjonskvalitet_nøyaktighethøyde real(20,0), kvalitet_posisjonskvalitet_maksimaltavvik real(20,0), prosesshistorie string(255), høydereferanse string(255), kommunenummer string(255), sideposisjon string(255), identifikasjon_identifikasjon_lokalid string(255), identifikasjon_identifikasjon_navnerom string(255), identifikasjon_identifikasjon_versjonid string(255), nettverk_nilreason string(255), nettverk_gml_remoteschema string(255), nettverk_xlink_href string(255), nettverk_owns integer, navn string(255), lenke___nilreason string(255), lenke___gml_remoteschema string(255), lenke___xlink_href string(255), lenke___owns integer
Veglenkesekvens (reader GML_1)
    attributes: endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, identifikasjon.Identifikasjon.lokalId xml_buffer, identifikasjon.Identifikasjon.navnerom xml_buffer, identifikasjon.Identifikasjon.versjonId xml_buffer, nettverk.nilReason xml_buffer, nettverk.gml_remoteSchema xml_buffer, nettverk.xlink_href xml_buffer, nettverk.owns xml_boolean, standardLRM xml_buffer, måltLengde xml_real64, sekvensdel{}.nilReason xml_buffer, sekvensdel{}.gml_remoteSchema xml_buffer, sekvensdel{}.xlink_href xml_buffer, sekvensdel{}.owns xml_boolean
    -> ListExploder
ListExploder
    ATTR_ACCUM_MODE = Merge Incoming List
    ATTR_CONFLICT_RES = Use Original
    LIST_ATTR = sekvensdel{}
    INDEX_ATTR = _element_index
    ELEMENTS -> AttributeRenamer_2
AttributeRenamer_2
    ATTR_TABLE:
      RENAME_SET_DEFAULT nettverk.xlink_href > nettverk
      RENAME_SET_DEFAULT xlink_href > sekvensdel
    -> StringReplacer_2
StringReplacer_2
    CASE = NO
    REGEXP = NO
    SRC_ATTRS = nettverk,sekvensdel
    FIND_TEXT = @Value(fme_basename).gml#
    NO_MATCH = _FME_NO_OP_
    -> FeatureMerger [input 1]
Veglenke (reader GML_1)
    attributes: endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, identifikasjon.Identifikasjon.lokalId xml_buffer, identifikasjon.Identifikasjon.navnerom xml_buffer, identifikasjon.Identifikasjon.versjonId xml_buffer, nettverk.nilReason xml_buffer, nettverk.gml_remoteSchema xml_buffer, nettverk.xlink_href xml_buffer, nettverk.owns xml_boolean, standardLRM xml_buffer, måltLengde xml_real64, startposisjon xml_real64, sluttposisjon xml_real64, sekvens.nilReason xml_buffer, sekvens.gml_remoteSchema xml_buffer, sekvens.xlink_href xml_buffer, sekvens.owns xml_boolean, sluttnode.nilReason xml_buffer,
      sluttnode.gml_remoteSchema xml_buffer, sluttnode.xlink_href xml_buffer, sluttnode.owns xml_boolean, startnode.nilReason xml_buffer, startnode.gml_remoteSchema xml_buffer, startnode.xlink_href xml_buffer, startnode.owns xml_boolean, typeVeg xml_buffer, detaljnivå xml_buffer, konnekteringslenke xml_boolean, feltoversikt xml_buffer, veglenkeFraDato xml_date, veglenkeTilDato xml_date, senterlinje xml_geometry, veglenkeadresse.Veglenkeadresse.kommunenummer xml_buffer, veglenkeadresse.Veglenkeadresse.adressekode xml_int64, veglenkeadresse.Veglenkeadresse.adressenavn xml_buffer, veglenkeadresse.Veglenkeadresse.sideveg xml_boolean, brøytes xml_boolean, trafikkreguleringer xml_buffer
    -> AttributeRenamer
AttributeRenamer
    ATTR_TABLE:
      RENAME_SET_DEFAULT nettverk.xlink_href > nettverk
      RENAME_SET_DEFAULT sekvens.xlink_href > sekvens
      RENAME_SET_DEFAULT startnode.xlink_href > startnode
      RENAME_SET_DEFAULT sluttnode.xlink_href > sluttnode
    -> StringReplacer
StringReplacer
    CASE = NO
    REGEXP = NO
    SRC_ATTRS = sekvens,startnode,nettverk,sluttnode
    FIND_TEXT = @Value(fme_basename).gml#
    NO_MATCH = _FME_NO_OP_
    -> FeatureMerger [input 2]
    -> veglenke (writer SPATIALITE_1)
FeatureMerger
    PROCESS_DUPS = No
    MERGE_TYPE = Geometry
    JOIN_KEYS = @Value(sekvensdel) @Value(gml_id) AUTO
    SUPPLIERS_FIRST = No
    NOT_MERGED -> Sekvensdeler_utenfor_aktuell_kommune
    MERGED -> Aggregator
Note: Todo: Koble Veglenke til sekvens, bygge agregert geometri
Aggregator
    AGGREGATE_TYPE = Homogeneous Collection (If Possible)
    SEP = ,
    MODE = Geometry - Assemble One Level
    ACCUM_ATTRS_NAME = No
    GROUP_BY = gml_id nettverk identifikasjon.Identifikasjon.navnerom identifikasjon.Identifikasjon.versjonId identifikasjon.Identifikasjon.lokalId
    ORDERED = No
    AGGREGATE -> veglenkesekvens (writer SPATIALITE_1)
veglenkesekvens (writer SPATIALITE_1)
    attributes: gml_id string(255), identifikasjon_identifikasjon_lokalid string(255), identifikasjon_identifikasjon_navnerom string(255), identifikasjon_identifikasjon_versjonid string(255), nettverk string(255)
Sekvensdeler_utenfor_aktuell_kommune: Logger
    MAXCOORDS = 20
    MESSAGE = Feature is:
    MAXFEATS = 20
veglenke (writer SPATIALITE_1)
    attributes: gml_id string(255), datafangstdato string(255), oppdateringsdato string(255), kvalitet_posisjonskvalitet_målemetode string(255), kvalitet_posisjonskvalitet_nøyaktighet real(20,0), kvalitet_posisjonskvalitet_synbarhet string(255), kvalitet_posisjonskvalitet_målemetodehøyde string(255), kvalitet_posisjonskvalitet_nøyaktighethøyde real(20,0), kvalitet_posisjonskvalitet_maksimaltavvik real(20,0), prosesshistorie string(255), høydereferanse string(255), kommunenummer string(255), identifikasjon_identifikasjon_lokalid string(255), identifikasjon_identifikasjon_navnerom string(255), identifikasjon_identifikasjon_versjonid string(255), nettverk string(255), standardlrm string(255), måltlengde real(31,15), startposisjon real(31,15), sluttposisjon real(31,15), sekvens string(255), sluttnode string(255), startnode string(255), typeveg string(255), detaljnivå string(255), konnekteringslenke integer, feltoversikt string(255), veglenkefradato string(255), veglenketildato string(255), senterlinje string(255),
      veglenkeadresse_veglenkeadresse_kommunenummer string(255), veglenkeadresse_veglenkeadresse_adressekode real(20,0), veglenkeadresse_veglenkeadresse_adressenavn string(255), veglenkeadresse_veglenkeadresse_sideveg integer, brøytes integer, trafikkreguleringer string(255)
