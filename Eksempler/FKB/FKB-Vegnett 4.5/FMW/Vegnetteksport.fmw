FME workspace Vegnetteksport.fmw
Title: Eksport av vegnett fra TNE

Parameters:
- knr = 403   # Kommunenummer (adskilt med komma)
- detaljNivå = Kjørefelt   # Detaljnivå
- geometriDimensjon = 2   # Geometrirepresentasjon
- OutputDirectory = C:\DATA\Standardisering\NVDB\GML   # Lagringsmappe
- txGMLFile1:   # Python Script
      KOMM=str(FME_MacroValues['knr']).zfill(4)
      par=FME_MacroValues['OutputDirectory']+ '\\FrittVegnettAssosiasjoner\\Data\\' + KOMM + FME_MacroValues['detaljNivå'] + "_" + FME_MacroValues['geometriDimensjon'] + 'd.gml'
      return par
- DestDataset_SPATIALITE:   # Python Script
      KOMM = str(FME_MacroValues['knr']).zfill(4)
      if FME_MacroValues['detaljNivå'] == 'Kjørefelt':
          dn = 'Kjorefelt'
      elif FME_MacroValues['detaljNivå'] == 'Kjørebane':
          dn = 'Kjorebane'
      else:
          dn = FME_MacroValues['detaljNivå']
      par = FME_MacroValues['OutputDirectory']+ '\\SpatiaLite\\' + KOMM + dn + '_' + FME_MacroValues['geometriDimensjon'] + 'd.db'
      return par
- txtGMLFile2:   # Python Script
      KOMM=str(FME_MacroValues['knr']).zfill(4)
      par=FME_MacroValues['OutputDirectory']+ '\\FrittVegnettAttributter\\Data\\' + KOMM + FME_MacroValues['detaljNivå'] + "_" + FME_MacroValues['geometriDimensjon'] + 'd.gml'
      return par
- navneromPrefix = http://www.vegvesen.no/nvdb/   # Felles del av navnerom

Writers:
- SPATIALITE_1: SPATIALITE to $(DestDataset_SPATIALITE)
- TEXTLINE_1: TEXTLINE to $(txGMLFile1)
- TEXTLINE_2: TEXTLINE to $(txtGMLFile2)

Creator
    NUM = 1
    GEOMTYPE = Geometry Object
    CREATED -> StringConcatenator
StringConcatenator
    PARM_LINE = TO_DATE = 99991231 AND KMNR_4584 IN ($(knr))
    VAL_ATTR = _concatenated
    -> FeatureReader_2
Note: Kommune(r)
FeatureReader_2
    GEODATABASE_SDE_RESOLVE_SUBTYPE_NAMES = yes
    WHERE = @Value(_concatenated)
    GEODATABASE_SDE_SPLIT_COMPLEX_EDGES = no
    FEATURETYPES = SDE_TNE.TNE_ST_Kommune_4710_10
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = Keep result attributes only
    GEODATABASE_SDE_REMOVE_TABLE_QUALIFIER = NO
    GEODATABASE_SDE_IGNORE_RELATIONSHIP_INFO = yes
    GEODATABASE_SDE_WHERE = TO_DATE = 99991231
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = SDE_TNE.TNE_ST_Kommune_4710_10
    GEODATABASE_SDE_SPLIT_MULTI_PART_ANNOS = no
    ATTRIBUTES = SDE_TNE.TNE_ST_Kommune_4710_10,"geodb_oid,OBJECTID,OID,NETOBJECTTV_ID,FROM_DATE,TO_DATE,BA_200700_OID,BA_201566_OID,KMNR_4584,KMNV_4585,KOORD_8146,SHAPE.AREA,SHAPE.LEN"
    GEODATABASE_SDE_RESOLVE_DOMAINS = no
    FORMAT = GEODATABASE_SDE
    GEODATABASE_SDE_CONNECTION_FILE = C:\Users\knjetl\AppData\Roaming\ESRI\Desktop10.1\ArcCatalog\TNE.sde
    GEODATABASE_SDE_IGNORE_NETWORK_INFO = yes
    SDE_TNE.TNE_ST_Kommune_4710_10 -> Kommune
    SDE_TNE.TNE_ST_Kommune_4710_10 -> FeatureReader
    SDE_TNE.TNE_ST_Kommune_4710_10 -> FeatureReader_3
Kommune: Inspector [off]
Note: CurveSegment, RefLinkPart og RefNode
FeatureReader
    GEODATABASE_SDE_RESOLVE_SUBTYPE_NAMES = yes
    WHERE = TO_DATE = 99991231
    INTERACT = INTERSECTS
    GEODATABASE_SDE_SPLIT_COMPLEX_EDGES = no
    FEATURETYPES = SDE_TNE.TNE_CurveSegment SDE_TNE.TNE_RefLinkPart SDE_TNE.TNE_RefNode
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = In case of conflict, keep result attributes
    GEODATABASE_SDE_REMOVE_TABLE_QUALIFIER = NO
    GEODATABASE_SDE_IGNORE_RELATIONSHIP_INFO = yes
    GEODATABASE_SDE_WHERE = TO_DATE = 99991231
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = SDE_TNE.TNE_CurveSegment SDE_TNE.TNE_RefNode SDE_TNE.TNE_RefLinkPart
    GEODATABASE_SDE_SPLIT_MULTI_PART_ANNOS = no
    ATTRIBUTES = SDE_TNE.TNE_CurveSegment,"geodb_oid,OBJECTID,REFLINK_OID,FROM_DATE,TO_DATE,FROM_MEASURE,TO_MEASURE,SEG_DATE,LENGTH,CLASS_CODE,OBJECT_CODE,MEDIUM,QUALITY_METHOD,QUALITY_ACCURACY,QUALITY_VISIBILITY,QUALITY_METHOD_HEIGHT,QUALITY_ACCURACY_HEIGHT,QUALITY_TOLERANCE,SHAPE.LEN",SDE_TNE.TNE_RefLinkPart,"geodb_oid,OBJECTID,REFLINK_OID,FROM_DATE,TO_DATE,FROM_MEASURE,TO_MEASURE,FROM_REFNODE_OID,TO_REFNODE_OID,LENGTH,TOPOLOGY_LEVEL,SUPER_OID,SUPER_FROM_MEASURE,SUPER_TO_MEASURE,LANE,DIRECTION,SHAPE.LEN",SDE_TNE.TNE_RefNode,"geodb_oid,OBJECTID,OID,VID,REFOBJ_TYPE,NEXT_FREE_PORT_NUMBER,FROM_DATE,TO_DATE"
    GEODATABASE_SDE_RESOLVE_DOMAINS = no
    FORMAT = GEODATABASE_SDE
    GEODATABASE_SDE_CONNECTION_FILE = C:\Users\knjetl\AppData\Roaming\ESRI\Desktop10.1\ArcCatalog\TNE.sde
    GEODATABASE_SDE_IGNORE_NETWORK_INFO = yes
    SDE_TNE.TNE_CurveSegment -> InlineQuerier [input 1]
    SDE_TNE.TNE_RefNode -> CoordinateRounder
    SDE_TNE.TNE_RefLinkPart -> PythonCaller_3
Note: Finner valgt detaljnivå
PythonCaller_3
    PYTHONSOURCE:
      import fmeobjects

      def topolevel(feature):
          par = '0,1,2,3'
          if FME_MacroValues['detaljNivå'] == 'Vegtrase':
              par = '0,1'
          elif FME_MacroValues['detaljNivå'] == 'Kjørebane':
              par = '1,2'
          elif FME_MacroValues['detaljNivå'] == 'Kjørefelt':
              par = '1,2,3'
          feature.setAttribute("_topoWhere", par)
    PYTHONSYMBOL = topolevel
    NEW_ATTRIBUTES = _topoWhere
    -> TestFilter_4
Note: Finner lenker som skal være med
TestFilter_4
    TEST_LIST = BOOL_OP,OR,COMPOSITE_TEST,<Unused>,TEST_CLAUSE,"TEST @Value(TOPOLOGY_LEVEL) IN @Value(_topoWhere)",TOPOLEVEL
    DEFAULT_VALUE = <UNFILTERED>
    TOPOLEVEL -> InlineQuerier [input 2]
Note: Kobler CurveSegment til / RefLinkPart
InlineQuerier
    QUERY_SCHEMA = RefLinkPartExtended,REFLINK_OID,text,FROM_MEASURE,text,TO_MEASURE,text,RefLinkPart.fme_feature_content,fme_feature_content,CurveSegment.fme_feature_content,fme_feature_content
    TABLE_DEF = CurveSegment,REFLINK_OID,text,FROM_MEASURE,text,TO_MEASURE,text,RefLinkPart,REFLINK_OID,text,FROM_MEASURE,text,TO_MEASURE,text
    QUERY_DEF:
      RefLinkPartExtended,SELECT DISTINCT * FROM RefLinkPart
      INNER JOIN CurveSegment ON RefLinkPart.REFLINK_OID = CurveSegment.REFLINK_OID
      WHERE (RefLinkPart.FROM_MEASURE < CurveSegment.TO_MEASURE AND RefLinkPart.TO_MEASURE > CurveSegment.FROM_MEASURE) ,FIRST
    RefLinkPartExtended -> DuplicateRemover
Note: Fjerner duplikater
DuplicateRemover
    KEYATTR = OBJECTID
    UNIQUE -> PythonCaller
Note: Avrunder til 2 desimaler
CoordinateRounder
    ZPREC = 2
    YPREC = 2
    XPREC = 2
    ROUNDED -> TopologyBuilder [input 1]
TestFilter_3
    TEST_LIST = BOOL_OP,OR,COMPOSITE_TEST,<Unused>,TEST_CLAUSE,"TEST @Value(_element_count) >= 1",Aktivenoder
    DEFAULT_VALUE = <UNFILTERED>
    Aktivenoder -> 2DForcer_2
Note: Tvinger 2D
2DForcer_2
    2D -> GeometryExtractor_3
GeometryExtractor_3
    ATTR = posisjon
    OMIT_NAMESPACES_DISPLAY = No
    KIND_LONG = GML v3.2.1
    -> XMLTemplaterFeature_2
    -> vegnode (writer SPATIALITE_1)
    -> XMLTemplaterFeature_3
Note: Vegnode (SpatiaLite)
vegnode (writer SPATIALITE_1)
    attributes: gml_id string(255), identifikasjon_identifikasjon_lokalid string(255), identifikasjon_identifikasjon_navnerom string(255), posisjon string(255)
AttributeRenamer_2
    ATTR_LIST = _from_gml_id,startnode_xlink_href,"",_to_gml_id,sluttnode_xlink_href,""
    -> StringConcatenator_2
Note: GML.id
StringConcatenator_2
    PARM_LINE = NVDB_ReferanseDellenker.@Value(identifikasjon_identifikasjon_lokalid)
    VAL_ATTR = gml_id
    -> StringConcatenator_3
Note: GML.ReflinkID
StringConcatenator_3
    PARM_LINE = NVDB_ReferanseLenker.@Value(sekvensidentifikasjon_identifikasjon_lokalid)
    VAL_ATTR = sekvensidentifikasjon_xlink_href
    -> DateFormatter
DateFormatter
    DATE_ATTR = veglenkefradato,veglenketildato
    FMT = ISO Date (%Y-%m-%d)
    SRCFMT = Unknown - Automatic Detection
    INVALID_DATE_VALUE = _FME_NO_OP_
    -> StringFormatter
StringFormatter
    SRC_ATTRS = kommune
    FORMAT = 04s
    -> NullAttributeMapper
NullAttributeMapper
    SOURCE_ATTR_VAL = Null "Missing (Selected Attributes Only)" Empty
    NULL_TREATMENT = Missing
    ATTRCHOICE = Selected Attributes
    ATTRLIST = kvalitet_posisjonskvalitet_målemetode kvalitet_posisjonskvalitet_nøyaktighet kvalitet_posisjonskvalitet_målemetodehøyde kvalitet_posisjonskvalitet_nøyaktighethøyde
    OTHER_VALUE = 0
    -> TestFilter_5
Note: Valgt geometrinivå
TestFilter_5
    TEST_LIST = BOOL_OP,OR,COMPOSITE_TEST,<Unused>,TEST_CLAUSE,"TEST $(geometriDimensjon) = 2",2D
    DEFAULT_VALUE = 3D
    2D -> 2DForcer
    3D -> GeometryExtractor
Note: Tvinger 2D
2DForcer
    2D -> GeometryExtractor
GeometryExtractor
    ATTR = senterlinje
    OMIT_NAMESPACES_DISPLAY = No
    KIND_LONG = GML v3.2.1
    -> veglenke (writer SPATIALITE_1)
    -> XMLTemplaterFeature
    -> XMLTemplaterFeature_4
Note: Veglenke (SpatiaLite)
veglenke (writer SPATIALITE_1)
    attributes: gml_id string(255), kvalitet_posisjonskvalitet_målemetode integer, kvalitet_posisjonskvalitet_nøyaktighet integer, kvalitet_posisjonskvalitet_målemetodehøyde integer, kvalitet_posisjonskvalitet_nøyaktighethøyde integer, medium string(1), kommune string(4), identifikasjon_identifikasjon_lokalid string(255), identifikasjon_identifikasjon_navnerom string(255), standardlrm integer, startverdi real(31,15), sluttverdi real(31,15), senterlinje string(255), detaljnivå string(50), konnekteringslenke string(5), typeveg string(50), veglenkefradato date, veglenketildato date, sekvensidentifikasjon_xlink_href string(255), startnode_xlink_href string(255), sluttnode_xlink_href string(255)

Bookmark: Døper om og mapper egenskaper
Note: Ordner nullverdier for kvalitetsattributter
PythonCaller
    PYTHONSOURCE:
      import fmeobjects
      # Template Function interface:
      def processFeature(feature):
          par=feature.getAttribute('QUALITY_METHOD')
          if par == -1 or par == 0:
              feature.removeAttribute('QUALITY_METHOD')
          par=feature.getAttribute('QUALITY_ACCURACY')
          if par == -1 or par == 0:
              feature.removeAttribute('QUALITY_ACCURACY')
          par=feature.getAttribute('QUALITY_METHOD_HEIGHT')
          if par == -1 or par == 0:
              feature.removeAttribute('QUALITY_METHOD_HEIGHT')
          par=feature.getAttribute('QUALITY_ACCURACY_HEIGHT')
          if par == -1 or par == 0:
              feature.removeAttribute('QUALITY_ACCURACY_HEIGHT')
    PYTHONSYMBOL = processFeature
    -> AttributeValueMapper_3
Note: medium
AttributeValueMapper_3
    DIRECTION = Forward (Source To Destination)
    VAL_ATTR = medium
    DEFAULT_VALUE = T
    LUT = 0,T,1,B,2,L,3,U
    SRC = MEDIUM
    -> AttributeCopier
AttributeCopier
    ATTR_LIST = OBJECTID,identifikasjon_identifikasjon_lokalid,"",REFLINK_OID,sekvensidentifikasjon_identifikasjon_lokalid,"",FROM_MEASURE,startverdi,"",TO_MEASURE,sluttverdi,""
    -> AttributeRenamer
AttributeRenamer
    ATTR_LIST = QUALITY_METHOD,kvalitet_posisjonskvalitet_målemetode,"",QUALITY_ACCURACY,kvalitet_posisjonskvalitet_nøyaktighet,"",QUALITY_METHOD_HEIGHT,kvalitet_posisjonskvalitet_målemetodehøyde,"",QUALITY_ACCURACY_HEIGHT,kvalitet_posisjonskvalitet_nøyaktighethøyde,"",KMNR_4584,kommune,"",FROM_DATE,veglenkefradato,"",TO_DATE,veglenketildato,""
    -> AttributeCreator
Note: navnerom og standardLRM
AttributeCreator
    ATTR_LIST = identifikasjon_identifikasjon_navnerom,$(navneromPrefix)referansedellenker/so,standardlrm,2,sekvensidentifikasjon_identifikasjon_navnerom,$(navneromPrefix)referanselenker/so
    -> AttributeValueMapper
Note: konnekteringslenke
AttributeValueMapper
    DIRECTION = Forward (Source To Destination)
    VAL_ATTR = konnekteringslenke
    DEFAULT_VALUE = false
    LUT = 7004,true
    SRC = CLASS_CODE
    -> AttributeValueMapper_2
Note: detaljNivå
AttributeValueMapper_2
    DIRECTION = Forward (Source To Destination)
    VAL_ATTR = detaljnivå
    LUT = 0,Vegtrase,2,Kjørebane,3,Kjørefelt
    SRC = TOPOLOGY_LEVEL
    -> TestFilter_2

Bookmark: Overodnet lenke for objekttypene Svingekonnekteringslenke og Kjørefelt
Note: Skiller ut / Svingekonnekteringslenker / og Kjørefeltlenker
TestFilter_2
    TEST_LIST = BOOL_OP,OR,COMPOSITE_TEST,<Unused>,TEST_CLAUSE,"TEST @Value(CLASS_CODE) = 7004",Svingekonnekteringslenke,BOOL_OP,OR,COMPOSITE_TEST,<Unused>,TEST_CLAUSE,"TEST @Value(CLASS_CODE) = 7010",Kjørefelt
    DEFAULT_VALUE = <UNFILTERED>
    <UNFILTERED> -> AttributeValueMapper_4
    Svingekonnekteringslenke -> BulkAttributeRenamer_2
    Kjørefelt -> BulkAttributeRenamer_2
    <UNFILTERED> -> InlineQuerier_2 [input 2]
BulkAttributeRenamer_2
    REPLACE_STR = FLD
    ATTRCHOICE = Selected Attributes
    PATTERN_ACTION_DISP = Add String Prefix
    ATTRLIST = CLASS_CODE
    -> InlineQuerier_2 [input 1]
Note: Koblertil overodnet lenke
InlineQuerier_2
    QUERY_SCHEMA = Ut,SUPER_OID,text,SUPER_FROM_MEASURE,text,SUPER_TO_MEASURE,text,OBJECTID,text,Kjørefelt.fme_feature_content,fme_feature_content,CLASS_CODE,text
    TABLE_DEF = Kjørefelt,SUPER_OID,text,SUPER_FROM_MEASURE,text,SUPER_TO_MEASURE,text,OBJECTID,text,Andre,REFLINK_OID,text,FROM_MEASURE,text,TO_MEASURE,text,CLASS_CODE,text
    QUERY_DEF:
      Ut,SELECT DISTINCT Kjørefelt.*, Andre.CLASS_CODE FROM Kjørefelt
      INNER JOIN Andre ON Kjørefelt.SUPER_OID = Andre.REFLINK_OID
      WHERE (Kjørefelt.SUPER_FROM_MEASURE < Andre.TO_MEASURE AND Kjørefelt.SUPER_TO_MEASURE > Andre.FROM_MEASURE) ,FIRST
    Ut -> DuplicateRemover_2
Note: Fjerner duplikater
DuplicateRemover_2
    KEYATTR = OBJECTID
    UNIQUE -> AttributeValueMapper_4

Bookmark: Type veg for alle lenker
Note: Mapping fra objekttype til typeVeg
AttributeValueMapper_4
    DIRECTION = Forward (Source To Destination)
    VAL_ATTR = typeveg
    DEFAULT_VALUE = Enkel bilveg
    LUT = 7001,Enkel bilveg,7012,Kanalisert veg,7011,Kanalisert veg,7201,Bilferje,7042,Gang- og sykkelveg,7046,Fortau,6304,Trapp
    SRC = CLASS_CODE
    -> InlineQuerier_3 [input 1]
Note: Vegreferanse / (Kun rundkjøringer)
FeatureReader_3
    GEODATABASE_SDE_RESOLVE_SUBTYPE_NAMES = yes
    WHERE = TO_DATE = 99991231 AND (HP_4569>= 400 AND HP_4569 <= 599)
    INTERACT = INTERSECTS
    GEODATABASE_SDE_SPLIT_COMPLEX_EDGES = no
    FEATURETYPES = SDE_TNE.TNE_FT_Vegreferanse_532_10
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = Keep result attributes only
    GEODATABASE_SDE_REMOVE_TABLE_QUALIFIER = NO
    GEODATABASE_SDE_IGNORE_RELATIONSHIP_INFO = yes
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = SDE_TNE.TNE_FT_Vegreferanse_532_10
    GEODATABASE_SDE_SPLIT_MULTI_PART_ANNOS = no
    ATTRIBUTES = SDE_TNE.TNE_FT_Vegreferanse_532_10,"geodb_oid,OBJECTID,NETOBJECTTV_ID,FROM_DATE,TO_DATE,SEQ_NO,FYNR_4591,KMNR_4592,VKTG_4566,VSOV_4570,VGNR_4568,HP_4569,VSTS_4567,FRMT_4571,TLMT_4572,BRK1_4576,BRK2_4577,VGTP_4574,FVKD_4573,ENRG_4707,SVTP_4575,MDAT_4578,ROUTE_ID,FROM_MEASURE,TO_MEASURE,DIRECTION,TOPOLOGY_LEVEL,SHAPE.LEN"
    GEODATABASE_SDE_RESOLVE_DOMAINS = no
    FORMAT = GEODATABASE_SDE
    GEODATABASE_SDE_CONNECTION_FILE = C:\Users\knjetl\AppData\Roaming\ESRI\Desktop10.1\ArcCatalog\TNE.sde
    GEODATABASE_SDE_IGNORE_NETWORK_INFO = yes
    SDE_TNE.TNE_FT_Vegreferanse_532_10 -> AttributeKeeper_2
AttributeKeeper_2
    KEEP_ATTRS = HP_4569,ROUTE_ID,FROM_MEASURE,TO_MEASURE
    -> InlineQuerier_3 [input 2]
Note: Kobler til Vegreferanse / (Rundkjøring)
InlineQuerier_3
    QUERY_SCHEMA = RefLinkPart,REFLINK_OID,text,FROM_MEASURE,text,TO_MEASURE,text,CLASS_CODE,text,RefLinkPart.fme_feature_content,fme_feature_content,Rundkjøringer,REFLINK_OID,text,FROM_MEASURE,text,TO_MEASURE,text,CLASS_CODE,text,RefLinkPart.fme_feature_content,fme_feature_content
    TABLE_DEF = RefLinkPart,REFLINK_OID,text,FROM_MEASURE,text,TO_MEASURE,text,CLASS_CODE,text,Vegreferanse,ROUTE_ID,text,FROM_MEASURE,text,TO_MEASURE,text,HP_4569,text
    QUERY_DEF:
      RefLinkPart,SELECT *
      FROM RefLinkPart,FIRST,Rundkjøringer,SELECT DISTINCT RefLinkPart.* FROM RefLinkPart
      INNER JOIN Vegreferanse ON RefLinkPart.REFLINK_OID = Vegreferanse.ROUTE_ID
      WHERE (RefLinkPart.FROM_MEASURE < Vegreferanse.TO_MEASURE AND RefLinkPart.TO_MEASURE > Vegreferanse.FROM_MEASURE) ,FIRST
    RefLinkPart -> FeatureMerger [input 1]
    Rundkjøringer -> DuplicateRemover_3
Note: Fjerner duplikater
DuplicateRemover_3
    KEYATTR = OBJECTID
    UNIQUE -> FeatureMerger [input 2]
Note: Finner lenker som er rundkjøring
FeatureMerger
    PROCESS_DUPS = No
    MERGE_TYPE = Attributes Only
    SUPPLIERS_FIRST = No
    JOIN_KEYS = @Value(OBJECTID) @Value(OBJECTID) AUTO
    SUPPLIER_PREFIX_DUMMY = YES
    MERGED -> AttributeCreator_2
    NOT_MERGED -> Snapper
Note: typeVeg=Rundkjøring
AttributeCreator_2
    ATTR_LIST = typeveg,Rundkjøring
    -> Snapper

Bookmark: Ordner geometri
Note: Snapper lenker innenfor 5 cm
Snapper
    SNAPTYPE_PARAM = End Point Snapping
    SAVE_SHORT_LINES = Yes
    TOLERANCE = 0.05
    EXTEND_LINES = NEVER
    UNTOUCHED -> CoordinateRounder_2
    SNAPPED -> CoordinateRounder_2
Note: 2 desimaler
CoordinateRounder_2
    ZPREC = 2
    YPREC = 2
    XPREC = 2
    ROUNDED -> TopologyBuilder [input 2]

Bookmark: Topologibygging med etablering av manglende noder
Note: Bygger topologi: / Lager manglende noder og finner sammenhenger mellom lenker og noder
TopologyBuilder
    OVERLAPPING_MODE = No
    PROP_ATTRS = No
    ALL_EDGES = Yes
    CLEAN_DATA = Yes
    ALLOW_CYCLES = No
    MAX = 0
    NODE -> TestFilter
    LINE -> FeatureMerger_2 [input 1]
Note: Identifiserer nye noder / (Pseudonoder)
TestFilter
    TEST_LIST = BOOL_OP,OR,COMPOSITE_TEST,<Unused>,TEST_CLAUSE,"TEST OID ATTRIBUTE_IS_MISSING """"",PseudoNode
    DEFAULT_VALUE = EksisterendeNode
    PseudoNode -> AttributeCreator_3
    EksisterendeNode -> AttributeCopier_2
Note: ID for nye noder
AttributeCreator_3
    ATTR_LIST = OID,p@Value(_node_number)
    -> AttributeCopier_2
AttributeCopier_2
    ATTR_LIST = OID,identifikasjon_identifikasjon_lokalid,""
    -> AttributeCreator_4
Note: Navnerom
AttributeCreator_4
    ATTR_LIST = identifikasjon_identifikasjon_navnerom,$(navneromPrefix)referansenoder/so
    -> StringConcatenator_4
Note: GML.ID
StringConcatenator_4
    PARM_LINE = NVDB_ReferanseNoder.@Value(identifikasjon_identifikasjon_lokalid)
    VAL_ATTR = gml_id
    -> ListElementCounter
    -> AttributeKeeper_3
ListElementCounter
    LIST_NAME = _node_angle{}
    CNT_ATTR = _element_count
    -> TestFilter_3
AttributeKeeper_3
    KEEP_ATTRS = identifikasjon_identifikasjon_lokalid,_node_number,identifikasjon_identifikasjon_navnerom,gml_id
    -> FeatureMerger_2 [input 2]
    -> FeatureMerger_3 [input 2]
Note: Kobler til franode
FeatureMerger_2
    PROCESS_DUPS = No
    MERGE_TYPE = Attributes Only
    SUPPLIER_PREFIX = _from_
    SUPPLIERS_FIRST = No
    JOIN_KEYS = @Value(_from_node) @Value(_node_number) AUTO
    SUPPLIER_PREFIX_DUMMY = YES
    MERGED -> FeatureMerger_3 [input 1]
    NOT_MERGED -> FeatureMerger_3 [input 1]
Note: Kobler til tilnode
FeatureMerger_3
    PROCESS_DUPS = No
    MERGE_TYPE = Attributes Only
    SUPPLIER_PREFIX = _to_
    SUPPLIERS_FIRST = No
    JOIN_KEYS = @Value(_to_node) @Value(_node_number) AUTO
    SUPPLIER_PREFIX_DUMMY = YES
    MERGED -> AttributeRenamer_2
    NOT_MERGED -> AttributeRenamer_2

Bookmark: GML-eksport til skjema med assosiasjoner realisert som attributter
XMLTemplaterFeature_3
    RESULT_ATTRIBUTE = _gml_feature
    ROOT_QUERY_EXPR:
      <Vegnode gml:id="{fme:get-attribute("gml_id")}"  xmlns="http://www.jetlundweb.no/geomatikk/GML/FrittVegnettAttributter/" xmlns:gml="http://www.opengis.net/gml/3.2" xmlns:xlink="http://www.w3.org/1999/xlink">
          <identifikasjon>
              <Identifikasjon>
                  <lokalId>{fme:get-attribute("identifikasjon_identifikasjon_lokalid")}</lokalId>
      			<navnerom>{fme:get-attribute("identifikasjon_identifikasjon_navnerom")}</navnerom>
      		</Identifikasjon>
      	</identifikasjon>
      	<posisjon>
              {fme:get-xml-attribute("posisjon")}
          </posisjon>
      </Vegnode>
    VISIBLE_QUERY_VALIDATE = No
    OUTPUT_XML_HEADER = No
    -> XMLValidator_3
XMLTemplaterFeature_4
    RESULT_ATTRIBUTE = _gml_feature
    ROOT_QUERY_EXPR:
      <Veglenke gml:id="{fme:get-attribute("gml_id")}"  xmlns="http://www.jetlundweb.no/geomatikk/GML/FrittVegnettAttributter/" xmlns:gml="http://www.opengis.net/gml/3.2" xmlns:xlink="http://www.w3.org/1999/xlink">
          {if( fme:has-attribute("kvalitet_posisjonskvalitet_målemetode") or fme:has-attribute("kvalitet_posisjonskvalitet_nøyaktighet")) then
          <kvalitet>
              <Posisjonskvalitet>
                  {if( fme:has-attribute("kvalitet_posisjonskvalitet_målemetode")) then <målemetode>{fme:get-attribute("kvalitet_posisjonskvalitet_målemetode")}</målemetode> else ()}
                  {if( fme:has-attribute("kvalitet_posisjonskvalitet_nøyaktighet"))  then <nøyaktighet>{fme:get-attribute("kvalitet_posisjonskvalitet_nøyaktighet")}</nøyaktighet> else ()}
                  {if( fme:has-attribute("kvalitet_posisjonskvalitet_målemetodehøyde"))  then <målemetodeHøyde>{fme:get-attribute("kvalitet_posisjonskvalitet_målemetodehøyde")}</målemetodeHøyde> else ()}
                  {if( fme:has-attribute("kvalitet_posisjonskvalitet_nøyaktighethøyde")) then <nøyaktighetHøyde>{fme:get-attribute("kvalitet_posisjonskvalitet_nøyaktighethøyde")}</nøyaktighetHøyde> else ()}
              </Posisjonskvalitet>
      	</kvalitet> else ()}
          <medium>{fme:get-attribute("medium")}</medium>
          <kommune>{fme:get-attribute("kommune")}</kommune>
          <identifikasjon>
              <Identifikasjon>
                  <lokalId>{fme:get-attribute("identifikasjon_identifikasjon_lokalid")}</lokalId>
      			<navnerom>{fme:get-attribute("identifikasjon_identifikasjon_navnerom")}</navnerom>
      		</Identifikasjon>
      	</identifikasjon>
      	<standardLRM>{fme:get-attribute("standardlrm")}</standardLRM>
          <sekvens>
              <Identifikasjon>
                  <lokalId>{fme:get-attribute("sekvensidentifikasjon_identifikasjon_lokalid")}</lokalId>
      			<navnerom>{fme:get-attribute("sekvensidentifikasjon_identifikasjon_navnerom")}</navnerom>
      		</Identifikasjon>
      	</sekvens>
      	<startVerdi>{fme:get-attribute("startverdi")}</startVerdi>
      	<sluttVerdi>{fme:get-attribute("sluttverdi")}</sluttVerdi>
      	<senterlinje>
              {fme:get-xml-attribute("senterlinje")}
      	</senterlinje>
          {if( fme:has-attribute("detaljnivå") and not(fme:get-attribute("detaljnivå") eq "") ) then <detaljNivå>{fme:get-attribute("detaljnivå")}</detaljNivå> else ()}
      	<konnekteringslenke>{fme:get-attribute("konnekteringslenke")}</konnekteringslenke>
      	<typeVeg>{fme:get-attribute("typeveg")}</typeVeg>
      	<veglenkeFraDato>{fme:get-attribute("veglenkefradato")}</veglenkeFraDato>
      	<veglenkeTilDato>{fme:get-attribute("veglenketildato")}</veglenkeTilDato>
          <startnode>
              <Identifikasjon>
                  <lokalId>{fme:get-attribute("_from_identifikasjon_identifikasjon_lokalid")}</lokalId>
      			<navnerom>{fme:get-attribute("_from_identifikasjon_identifikasjon_navnerom")}</navnerom>
      		</Identifikasjon>
      	</startnode>
          <sluttnode>
              <Identifikasjon>
                  <lokalId>{fme:get-attribute("_to_identifikasjon_identifikasjon_lokalid")}</lokalId>
      			<navnerom>{fme:get-attribute("_to_identifikasjon_identifikasjon_navnerom")}</navnerom>
      		</Identifikasjon>
      	</sluttnode>
       </Veglenke>
    VISIBLE_QUERY_VALIDATE = No
    OUTPUT_XML_HEADER = No
    -> XMLValidator_3
XMLValidator_3
    VAL_MODE_1 = Syntax Only
    XML_ATTR_TEXT = _gml_feature
    LIST_NAME = _xml_features
    XML_INPUT_TYPE = Attribute Specifying XML Text
    LIMIT_ERRORS = No
    PASSED -> AttributeKeeper_4
AttributeKeeper_4
    KEEP_ATTRS = _gml_feature
    -> Aggregator_2
Aggregator_2
    MODE = Geometry - Assemble One Level
    ACCUM_ATTRS_NAME = No
    LIST_NAME = _featurelist
    SEP = ,
    AGGREGATE_TYPE = Multiple Geometry
    ORDERED = No
    AGGREGATE -> BoundsExtractor_2
BoundsExtractor_2
    YMIN = _ymin
    ZMIN = _zmin
    XMIN = _xmin
    XMAX = _xmax
    ZMAX = _zmax
    YMAX = _ymax
    -> XMLTemplaterDataset_2
XMLTemplaterDataset_2
    RESULT_ATTRIBUTE = _xml_dataset
    ROOT_QUERY_EXPR:
      <?xml version="1.0" encoding="UTF-8"?>
      <gml:FeatureCollection gml:id="Vegnett.$(knr)"
          xsi:schemaLocation="http://www.jetlundweb.no/geomatikk/GML/FrittVegnettAttributter/
                              http://www.jetlundweb.no/geomatikk/GML/FrittVegnettAttributter/FrittVegnettAttributter.xsd"
          xmlns="http://www.jetlundweb.no/geomatikk/GML/FrittVegnettAttributter/"
          xmlns:gml="http://www.opengis.net/gml/3.2"
          xmlns:xlink="http://www.w3.org/1999/xlink"
          xmlns:xsi="http://www.w3.org/2001/XMLSchema-instance">

      <gml:boundedBy>
          <gml:Envelope srsName="{fme:get-coordinate-system()}" srsDimension="{geom:get-dimension()}">
              {if( {geom:get-dimension()} = 3) then <gml:lowerCorner>{fme:get-attribute("_xmin")} {fme:get-attribute("_ymin")} {fme:get-attribute("_zmin")}</gml:lowerCorner> else <gml:lowerCorner>{fme:get-attribute("_xmin")} {fme:get-attribute("_ymin")} </gml:lowerCorner> }
              {if( {geom:get-dimension()} = 3) then <gml:upperCorner>{fme:get-attribute("_xmax")} {fme:get-attribute("_ymax")} {fme:get-attribute("_zmax")}</gml:upperCorner> else <gml:upperCorner>{fme:get-attribute("_xmax")} {fme:get-attribute("_ymax")}</gml:upperCorner> }
          </gml:Envelope>
      </gml:boundedBy>

      <gml:featureMembers>{fme:get-xml-list-attribute("_featurelist{}._gml_feature")}</gml:featureMembers>
      </gml:FeatureCollection>
    VISIBLE_QUERY_VALIDATE = No
    OUTPUT_XML_HEADER = Yes
    -> XMLFormatter_2
XMLFormatter_2
    REMOVE_EMPTY_ELEMENT = No
    XML_OUTPUT_ATTR = text_line_data
    OUTPUT_ENCODING = utf-8
    XML_ATTR_TEXT = _xml_dataset
    FORMATTING_CHOICE = Pretty-Print XML
    NAMESPACE_CLEANUP = Yes
    LIST_NAME = _xml_error
    COLLAPSE_EMPTY_ELEMENT = Yes
    SCHEMALOC_CLEANUP = No
    XML_INPUT_TYPE = Attribute Specifying XML Text
    XML_OUTPUT_TYPE = Attribute
    WHITESPACE_HANDLING = Remove excess whitespace
    REMOVE_ALL_COMMENT = No
    PASSED -> XMLValidator_4
XMLValidator_4
    VAL_MODE_1 = Syntax and Schema
    SCHEMA_LOC = C:\DATA\Standardisering\NVDB\GML\FrittVegnettAttributter\FrittVegnettAttributter.xsd
    XML_ATTR_TEXT = text_line_data
    LIST_NAME = _xml_error
    XML_INPUT_TYPE = Attribute Specifying XML Text
    LIMIT_ERRORS = No
    PASSED -> text_line (writer TEXTLINE_2)
    FAILED -> text_line (writer TEXTLINE_2)
text_line (writer TEXTLINE_2)
    attributes: text_line_data buffer

Bookmark: GML-eksport til skjema med assosiasjoner realisert som xlink:href
XMLTemplaterFeature_2
    RESULT_ATTRIBUTE = _gml_feature
    ROOT_QUERY_EXPR:
      <Vegnode gml:id="{fme:get-attribute("gml_id")}"  xmlns="http://www.jetlundweb.no/geomatikk/GML/FrittVegnettAssosiasjoner/" xmlns:gml="http://www.opengis.net/gml/3.2" xmlns:xlink="http://www.w3.org/1999/xlink">
          <identifikasjon>
              <Identifikasjon>
                  <lokalId>{fme:get-attribute("identifikasjon_identifikasjon_lokalid")}</lokalId>
      			<navnerom>{fme:get-attribute("identifikasjon_identifikasjon_navnerom")}</navnerom>
      		</Identifikasjon>
      	</identifikasjon>
      	<posisjon>
              {fme:get-xml-attribute("posisjon")}
          </posisjon>
      </Vegnode>
    VISIBLE_QUERY_VALIDATE = No
    OUTPUT_XML_HEADER = No
    -> XMLValidator_2
XMLTemplaterFeature
    RESULT_ATTRIBUTE = _gml_feature
    ROOT_QUERY_EXPR:
      <Veglenke gml:id="{fme:get-attribute("gml_id")}"  xmlns="http://www.jetlundweb.no/geomatikk/GML/FrittVegnettAssosiasjoner/" xmlns:gml="http://www.opengis.net/gml/3.2" xmlns:xlink="http://www.w3.org/1999/xlink">
          {if( fme:has-attribute("kvalitet_posisjonskvalitet_målemetode") or fme:has-attribute("kvalitet_posisjonskvalitet_nøyaktighet")) then
          <kvalitet>
              <Posisjonskvalitet>
                  {if( fme:has-attribute("kvalitet_posisjonskvalitet_målemetode")) then <målemetode>{fme:get-attribute("kvalitet_posisjonskvalitet_målemetode")}</målemetode> else ()}
                  {if( fme:has-attribute("kvalitet_posisjonskvalitet_nøyaktighet"))  then <nøyaktighet>{fme:get-attribute("kvalitet_posisjonskvalitet_nøyaktighet")}</nøyaktighet> else ()}
                  {if( fme:has-attribute("kvalitet_posisjonskvalitet_målemetodehøyde"))  then <målemetodeHøyde>{fme:get-attribute("kvalitet_posisjonskvalitet_målemetodehøyde")}</målemetodeHøyde> else ()}
                  {if( fme:has-attribute("kvalitet_posisjonskvalitet_nøyaktighethøyde")) then <nøyaktighetHøyde>{fme:get-attribute("kvalitet_posisjonskvalitet_nøyaktighethøyde")}</nøyaktighetHøyde> else ()}
              </Posisjonskvalitet>
      	</kvalitet> else ()}
          <medium>{fme:get-attribute("medium")}</medium>
          <kommune>{fme:get-attribute("kommune")}</kommune>
          <identifikasjon>
              <Identifikasjon>
                  <lokalId>{fme:get-attribute("identifikasjon_identifikasjon_lokalid")}</lokalId>
      			<navnerom>{fme:get-attribute("identifikasjon_identifikasjon_navnerom")}</navnerom>
      		</Identifikasjon>
      	</identifikasjon>
      	<standardLRM>{fme:get-attribute("standardlrm")}</standardLRM>
      	<startVerdi>{fme:get-attribute("startverdi")}</startVerdi>
      	<sluttVerdi>{fme:get-attribute("sluttverdi")}</sluttVerdi>
      	<senterlinje>
              {fme:get-xml-attribute("senterlinje")}
      	</senterlinje>
          {if( fme:has-attribute("detaljnivå") and not(fme:get-attribute("detaljnivå") eq "") ) then <detaljNivå>{fme:get-attribute("detaljnivå")}</detaljNivå> else ()}
      	<konnekteringslenke>{fme:get-attribute("konnekteringslenke")}</konnekteringslenke>
      	<typeVeg>{fme:get-attribute("typeveg")}</typeVeg>
      	<veglenkeFraDato>{fme:get-attribute("veglenkefradato")}</veglenkeFraDato>
      	<veglenkeTilDato>{fme:get-attribute("veglenketildato")}</veglenkeTilDato>
      	<sekvens xlink:href="#{fme:get-attribute("sekvensidentifikasjon_xlink_href")}" />
          <startnode xlink:href="#{fme:get-attribute("startnode_xlink_href")}" />
      	<sluttnode xlink:href="#{fme:get-attribute("sluttnode_xlink_href")}" />
      </Veglenke>
    VISIBLE_QUERY_VALIDATE = No
    OUTPUT_XML_HEADER = No
    -> XMLValidator_2
XMLValidator_2
    VAL_MODE_1 = Syntax Only
    XML_ATTR_TEXT = _gml_feature
    LIST_NAME = _xml_features
    XML_INPUT_TYPE = Attribute Specifying XML Text
    LIMIT_ERRORS = No
    PASSED -> AttributeKeeper
AttributeKeeper
    KEEP_ATTRS = _gml_feature
    -> Aggregator
Aggregator
    MODE = Geometry - Assemble One Level
    ACCUM_ATTRS_NAME = No
    LIST_NAME = _featurelist
    SEP = ,
    AGGREGATE_TYPE = Multiple Geometry
    ORDERED = No
    AGGREGATE -> BoundsExtractor
BoundsExtractor
    YMIN = _ymin
    ZMIN = _zmin
    XMIN = _xmin
    XMAX = _xmax
    ZMAX = _zmax
    YMAX = _ymax
    -> XMLTemplaterDataset
XMLTemplaterDataset
    RESULT_ATTRIBUTE = _xml_dataset
    ROOT_QUERY_EXPR:
      <?xml version="1.0" encoding="UTF-8"?>
      <gml:FeatureCollection gml:id="Vegnett.$(knr)"
          xsi:schemaLocation="http://www.jetlundweb.no/geomatikk/GML/FrittVegnettAssosiasjoner/
                              http://www.jetlundweb.no/geomatikk/GML/FrittVegnettAssosiasjoner/FrittVegnettAssosiasjoner.xsd"
          xmlns="http://www.jetlundweb.no/geomatikk/GML/FrittVegnettAssosiasjoner/"
          xmlns:gml="http://www.opengis.net/gml/3.2"
          xmlns:xlink="http://www.w3.org/1999/xlink"
          xmlns:xsi="http://www.w3.org/2001/XMLSchema-instance">

      <gml:boundedBy>
          <gml:Envelope srsName="{fme:get-coordinate-system()}" srsDimension="{geom:get-dimension()}">
              {if( {geom:get-dimension()} = 3) then <gml:lowerCorner>{fme:get-attribute("_xmin")} {fme:get-attribute("_ymin")} {fme:get-attribute("_zmin")}</gml:lowerCorner> else <gml:lowerCorner>{fme:get-attribute("_xmin")} {fme:get-attribute("_ymin")} </gml:lowerCorner> }
              {if( {geom:get-dimension()} = 3) then <gml:upperCorner>{fme:get-attribute("_xmax")} {fme:get-attribute("_ymax")} {fme:get-attribute("_zmax")}</gml:upperCorner> else <gml:upperCorner>{fme:get-attribute("_xmax")} {fme:get-attribute("_ymax")}</gml:upperCorner> }
          </gml:Envelope>
      </gml:boundedBy>

      <gml:featureMembers>{fme:get-xml-list-attribute("_featurelist{}._gml_feature")}</gml:featureMembers>
      </gml:FeatureCollection>
    VISIBLE_QUERY_VALIDATE = No
    OUTPUT_XML_HEADER = Yes
    -> XMLFormatter_3
XMLFormatter_3
    REMOVE_EMPTY_ELEMENT = No
    XML_OUTPUT_ATTR = text_line_data
    OUTPUT_ENCODING = utf-8
    XML_ATTR_TEXT = _xml_dataset
    FORMATTING_CHOICE = Pretty-Print XML
    NAMESPACE_CLEANUP = Yes
    LIST_NAME = _xml_error
    COLLAPSE_EMPTY_ELEMENT = Yes
    SCHEMALOC_CLEANUP = No
    XML_INPUT_TYPE = Attribute Specifying XML Text
    XML_OUTPUT_TYPE = Attribute
    WHITESPACE_HANDLING = Remove excess whitespace
    REMOVE_ALL_COMMENT = No
    PASSED -> XMLValidator
XMLValidator
    VAL_MODE_1 = Syntax and Schema
    SCHEMA_LOC = C:\DATA\Standardisering\NVDB\GML\FrittVegnettAssosiasjoner\FrittVegnettAssosiasjoner.xsd
    XML_ATTR_TEXT = text_line_data
    LIST_NAME = _xml_error
    XML_INPUT_TYPE = Attribute Specifying XML Text
    LIMIT_ERRORS = No
    PASSED -> text_line (writer TEXTLINE_1)
    FAILED -> text_line (writer TEXTLINE_1)
text_line (writer TEXTLINE_1)
    attributes: text_line_data buffer
