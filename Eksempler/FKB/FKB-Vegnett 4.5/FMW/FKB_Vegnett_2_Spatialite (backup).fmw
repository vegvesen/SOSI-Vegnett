FME workspace FKB_Vegnett_2_Spatialite (backup).fmw

Parameters:
- SourceDataset_GDMMAPPERSOSI = $(FME_MF_DIR)45\0403Vegnett45_KJ_Lekeversjon.SOS   # Source GDM File
- DestDataset_SPATIALITE = $(FME_MF_DIR)0403.db   # Destination SpatiaLite Database File
- DestDataset_GDMMAPPERQUADRI = $(FME_MF_DIR)45\Vegnett45.gdd   # Quadri_Files(*.gdd) Destination Quadri 

Readers:
- GDMMAPPERSOSI_1: GDMMAPPERSOSI from $(SourceDataset_GDMMAPPERSOSI)

Writers:
- SPATIALITE_1: SPATIALITE to $(DestDataset_SPATIALITE)
- GDMMAPPERQUADRI_1: GDMMAPPERQUADRI to $(DestDataset_GDMMAPPERQUADRI) in EPSG:25833

Veglenke (reader GDMMAPPERSOSI_1)
    attributes: DATAFANGSTDATO number(9,0), IDENT.LOKALID number(10,0), IDENT.NAVNEROM char(21), KOMM number(4,0), KONNEKTERINGSLENKE char(3), KVALITET.H-MÅLEMETODE number(3,0), KVALITET.H-NØYAKTIGHET number(4,0), KVALITET.MÅLEMETODE number(3,0), KVALITET.NØYAKTIGHET number(4,0), KVALITET.SYNBARHET number(2,0), LRLRM number(2,0), MEDIUM char(2), OBJTYPE char(9), TRAFIKKREGULERINGER char(31), TYPEVEG char(19), VEGDETALJNIVÅ char(10), VEGLENKEADRESSE.ADDRESSEKODE number(5,0), VEGLENKEADRESSE.ADDRESSENAVN char(23), VEGLENKEADRESSE.KOMM number(4,0), VEGLENKEADRESSE.SIDEVEG char(3), VFRADATO number(9,0), VKJORFELT char(8), VNR.VEGKATEGORI char(2), VNR.VEGNUMMER number(6,0), VNR.VEGSTATUS char(2), VPA.HOVEDPARSELL number(4,0), VPA.METER-FRA number(6,0), VPA.METER-TIL number(6,0), LRSTARTVERDI number(10,0), LRSLUTTVERDI number(10,0),
      LRMÅLTLENGDE number(10,0)
    -> SOSI_LRverdier_Heltall
    -> Veglenke (writer GDMMAPPERQUADRI_1)
Veglenke (writer GDMMAPPERQUADRI_1)
    attributes: DATAFANGSTDATO number(9,0), IDENT.LOKALID number(10,0), IDENT.NAVNEROM char(21), KOMM number(4,0), KONNEKTERINGSLENKE char(3), KVALITET.H-MÅLEMETODE number(3,0), KVALITET.H-NØYAKTIGHET number(4,0), KVALITET.MÅLEMETODE number(3,0), KVALITET.NØYAKTIGHET number(4,0), KVALITET.SYNBARHET number(2,0), LRLRM number(2,0), MEDIUM char(2), OBJTYPE char(9), TRAFIKKREGULERINGER char(31), TYPEVEG char(19), VEGDETALJNIVÅ char(10), VEGLENKEADRESSE.ADDRESSEKODE number(5,0), VEGLENKEADRESSE.ADDRESSENAVN char(23), VEGLENKEADRESSE.KOMM number(4,0), VEGLENKEADRESSE.SIDEVEG char(3), VFRADATO number(9,0), VKJORFELT char(8), VNR.VEGKATEGORI char(2), VNR.VEGNUMMER number(6,0), VNR.VEGSTATUS char(2), VPA.HOVEDPARSELL number(4,0), VPA.METER-FRA number(6,0), VPA.METER-TIL number(6,0), LRSTARTVERDI number(10,0), LRSLUTTVERDI number(10,0),
      LRMÅLTLENGDE number(10,0)
SOSI_LRverdier_Heltall
    -> GeometryFilter_8
GeometryFilter_8
    BREAK_AGG = Yes
    LINE -> StringConcatenator
    LINE -> AttributeCopier_2
AttributeCopier_2
    ATTR_LIST = ident_lokalid,IDENT.LOKALID,ident_navnerom,IDENT.NAVNEROM,standardlrm,LRLRM,kommune,KOMM,trafikkreguleringer,TRAFIKKREGULERINGER,typeveg,TYPEVEG,vegdetaljnivaa,VEGDETALJNIVÅ,datafangstdato,DATAFANGSTDATO,konnekteringslenke,KONNEKTERINGSLENKE,veglenkeadresse_addressekode,VEGLENKEADRESSE.ADDRESSEKODE,veglenkeadresse_addressenavn,VEGLENKEADRESSE.ADDRESSENAVN,veglenkeadresse_komm,VEGLENKEADRESSE.KOMM,veglenkeadresse_sideveg,VEGLENKEADRESSE.SIDEVEG,feltoversikt,VKJORFELT,vegkategori,VNR.VEGKATEGORI,vegnummer,VNR.VEGNUMMER,vegstatus,VNR.VEGSTATUS,hovedparsell,VPA.HOVEDPARSELL,meter_fra,VPA.METER-FRA,meter_til,VPA.METER-TIL,veglenkefradato,VFRADATO,medium,MEDIUM,maalemetode,KVALITET.MÅLEMETODE,noeyaktighet,KVALITET.NØYAKTIGHET,synbarhet,KVALITET.SYNBARHET,horisontalmaalemetode,KVALITET.H-MÅLEMETODE,horisontalnoeyaktighet,KVALITET.H-NØYAKTIGHET
    -> veglenke (writer SPATIALITE_1)
veglenke (writer SPATIALITE_1) [off]
    attributes: ident_lokalid real(10,0), ident_navnerom string(21), standardlrm integer, kommune integer, trafikkreguleringer string(31), typeveg string(19), vegdetaljnivaa string(10), datafangstdato integer, konnekteringslenke string(3), veglenkeadresse_addressekode integer, veglenkeadresse_addressenavn string(23), veglenkeadresse_komm integer, veglenkeadresse_sideveg string(3), feltoversikt string(8), vegkategori string(2), vegnummer integer, vegstatus string(2), hovedparsell integer, meter_fra integer, meter_til integer, veglenkefradato integer, medium string(2), maalemetode integer, noeyaktighet integer, synbarhet integer, horisontalmaalemetode integer, horisontalnoeyaktighet integer
StringConcatenator
    PARM_LINE = @Value(IDENT.NAVNEROM)_@Value(IDENT.LOKALID)
    VAL_ATTR = _ident
    -> AttributeRemover
AttributeRemover
    REMOVE_ATTRS = DATAFANGSTDATO,IDENT.LOKALID,IDENT.NAVNEROM,KOMM,KONNEKTERINGSLENKE,KVALITET.H-MÅLEMETODE,KVALITET.H-NØYAKTIGHET,KVALITET.MÅLEMETODE,KVALITET.NØYAKTIGHET,KVALITET.SYNBARHET,LRLRM,MEDIUM,OBJTYPE,TRAFIKKREGULERINGER,TYPEVEG,VEGDETALJNIVÅ,VEGLENKEADRESSE.ADDRESSEKODE,VEGLENKEADRESSE.ADDRESSENAVN,VEGLENKEADRESSE.KOMM,VEGLENKEADRESSE.SIDEVEG,VFRADATO,VKJORFELT,VNR.VEGKATEGORI,VNR.VEGNUMMER,VNR.VEGSTATUS,VPA.HOVEDPARSELL,VPA.METER-FRA,VPA.METER-TIL
    -> EventGeometry [input 1]
    -> Svingerestriksjonsgeometri [input 2]
Vegsperring (reader GDMMAPPERSOSI_1)
    attributes: OBJTYPE char(12), VEGSPERRINGTYPE char(10), LRPUNKT.LROBJREF.LOKALID number(10,0), LRPUNKT.LROBJREF.NAVNEROM char(21), LRPUNKT.LRPUNKTPOSISJON number(3,0)
    -> AttributeCopier
Jernbanekryssing (reader GDMMAPPERSOSI_1)
    attributes: NVDB_TYPEJERNBANEKRYSSING char(10), OBJTYPE char(17), LRPUNKT.LROBJREF.LOKALID number(10,0), LRPUNKT.LROBJREF.NAVNEROM char(21), LRPUNKT.LRPUNKTPOSISJON number(4,0)
    -> AttributeCopier
AttributeCopier
    ATTR_LIST = LRSTREKNING.LROBJREF.LOKALID,LRPUNKT.LROBJREF.LOKALID,LRSTREKNING.LROBJREF.NAVNEROM,LRPUNKT.LROBJREF.NAVNEROM,LRSTREKNING.LRFRAPOSISJON,LRPUNKT.LRPUNKTPOSISJON,LRSTREKNING.LRTILPOSISJON,LRPUNKT.LRPUNKTPOSISJON
    -> StringConcatenator_2
Svingerestriksjon (reader GDMMAPPERSOSI_1)
    attributes: NVDB_MERKNAD char(21), NVDB_SVINGEFORBUDFRAID.LOKALID number(10,0), NVDB_SVINGEFORBUDFRAID.NAVNEROM char(21), NVDB_SVINGEFORBUDTILID.LOKALID number(10,0), NVDB_SVINGEFORBUDTILID.NAVNEROM char(21), OBJTYPE char(18)
    -> Svingerestriksjonsgeometri [input 1]
Svingerestriksjonsgeometri
    Utdata -> AttributeCopier_3
AttributeCopier_3
    ATTR_LIST = merknad,NVDB_MERKNAD,svingeforbudfraid_lokalid,NVDB_SVINGEFORBUDFRAID.LOKALID,svingeforbudfraid_navnerom,NVDB_SVINGEFORBUDFRAID.NAVNEROM,svingeforbudtilid_lokalid,NVDB_SVINGEFORBUDTILID.LOKALID,svingeforbudtilid_navnerom,NVDB_SVINGEFORBUDTILID.NAVNEROM
    -> svingerestriksjon (writer SPATIALITE_1)
svingerestriksjon (writer SPATIALITE_1) [off]
    attributes: merknad string(21), svingeforbudfraid_lokalid real(10,0), svingeforbudfraid_navnerom string(21), svingeforbudtilid_lokalid real(10,0), svingeforbudtilid_navnerom string(21)
Bruksklasse (reader GDMMAPPERSOSI_1)
    attributes: LRSTREKNING.LRFRAPOSISJON number(4,0), LRSTREKNING.LROBJREF.LOKALID number(10,0), LRSTREKNING.LROBJREF.NAVNEROM char(21), LRSTREKNING.LRTILPOSISJON number(5,0), NVDB_BRUKSKLASSEHELÅR char(15), NVDB_BRUKSKLASSETELE char(14), NVDB_BRUKSKLASSEVINTER char(15), NVDB_MAKSTOTALVEKTMODULVOGNTOG number(5,2), NVDB_MAKSTOTALVEKTTØMMERTRANSPORT number(5,2), NVDB_MAKSVOGNTOGLENGDE number(6,0), NVDB_STREKNINGSBESKRIVELSE char(73), NVDB_STREKNINGSBESKRIVELSEMODULVOGNTOG char(42), NVDB_VEGGRUPPE char(2), OBJTYPE char(12)
    -> StringConcatenator_2
Fartsgrense (reader GDMMAPPERSOSI_1)
    attributes: LRSTREKNING.LRFRAPOSISJON number(5,0), LRSTREKNING.LROBJREF.LOKALID number(10,0), LRSTREKNING.LROBJREF.NAVNEROM char(21), LRSTREKNING.LRTILPOSISJON number(5,0), NVDB_ARKIVNUMMER number(11,0), NVDB_FARTSGRENSEVERDI number(3,0), NVDB_VEDTAKSNUMMER char(22), OBJTYPE char(12)
    -> StringConcatenator_2
Høydebegrensning (reader GDMMAPPERSOSI_1)
    attributes: LRSTREKNING.LRFRAPOSISJON number(4,0), LRSTREKNING.LROBJREF.LOKALID number(10,0), LRSTREKNING.LROBJREF.NAVNEROM char(21), LRSTREKNING.LRTILPOSISJON number(4,0), NVDB_BREDDE number(5,2), NVDB_HMINHØYREKANT number(4,2), NVDB_HMINMIDT number(4,2), NVDB_HMINVENSTREKANT number(4,2), NVDB_NAVN char(12), NVDB_SKILTAHØYDE number(3,1), NVDB_TYPEHINDERHØYDEBEGRENSNING char(14), OBJTYPE char(17)
    -> StringConcatenator_2
InnkjøringForbudt (reader GDMMAPPERSOSI_1)
    attributes: LRSTREKNING.LRFRAPOSISJON number(2,0), LRSTREKNING.LROBJREF.LOKALID number(10,0), LRSTREKNING.LROBJREF.NAVNEROM char(21), LRSTREKNING.LRTILPOSISJON number(4,0), NVDB_MERKNAD char(19), NVDB_SKILTNUMMER number(4,0), OBJTYPE char(18), NVDB_FORBUDRETNINGSKODE number(2,0)
    -> StringConcatenator_2
Landbruksvegklasse (reader GDMMAPPERSOSI_1)
    attributes: LRSTREKNING.LRFRAPOSISJON number(2,0), LRSTREKNING.LROBJREF.LOKALID number(10,0), LRSTREKNING.LROBJREF.NAVNEROM char(21), LRSTREKNING.LRTILPOSISJON number(5,0), NVDB_KLASSELANDBRUKSVEG char(15), OBJTYPE char(19)
    -> StringConcatenator_2
StringConcatenator_2
    PARM_LINE = @Value(LRSTREKNING.LROBJREF.NAVNEROM)_@Value(LRSTREKNING.LROBJREF.LOKALID)
    VAL_ATTR = _ident
    -> Counter
Counter
    SCOPE = Global
    START = 0
    DOMAIN = counter
    CNT_ATTR = _count
    -> EventGeometry [input 2]
EventGeometry
    _rlRouteID = @Value(_ident)
    _rlTo = @Value(LRSLUTTVERDI)
    _rlFrom = @Value(LRSTARTVERDI)
    _measureMode = 3D
    _eventRouteID = @Value(_ident)
    _eventFrom = @Value(LRSTREKNING.LRFRAPOSISJON)
    _eventTo = @Value(LRSTREKNING.LRTILPOSISJON)
    _dimension = 3
    Lines -> Skjemamapping
    Points -> Skjemamapping
Skjemamapping: AttributeCopier
    ATTR_LIST = lrobjref_lokalid,LRSTREKNING.LROBJREF.LOKALID,typekryssing,NVDB_TYPEJERNBANEKRYSSING,posisjon,LRPUNKT.LRPUNKTPOSISJON,vegsperringtype,VEGSPERRINGTYPE,klasse,NVDB_KLASSELANDBRUKSVEG,merknad,NVDB_MERKNAD,skiltnummer,NVDB_SKILTNUMMER,lrobjref_navnerom,LRSTREKNING.LROBJREF.NAVNEROM,fraposisjon,LRSTREKNING.LRFRAPOSISJON,tilposisjon,LRSTREKNING.LRTILPOSISJON,bruksklassehelaar,NVDB_BRUKSKLASSEHELÅR,bruksklassetele,NVDB_BRUKSKLASSETELE,bruksklassevinter,NVDB_BRUKSKLASSEVINTER,makstotalvektmodulvogntog,NVDB_MAKSTOTALVEKTMODULVOGNTOG,makstotalvekttoemmertransport,NVDB_MAKSTOTALVEKTTØMMERTRANSPORT,maksvogntoglengde,NVDB_MAKSVOGNTOGLENGDE,strekningsbeskrivelse,NVDB_STREKNINGSBESKRIVELSE,strekningsbeskrivelsemodulvogntog,NVDB_STREKNINGSBESKRIVELSEMODULVOGNTOG,veggruppe,NVDB_VEGGRUPPE,arkivnummer,NVDB_ARKIVNUMMER,fartsgrenseverdi,NVDB_FARTSGRENSEVERDI,vedtaksnummer,NVDB_VEDTAKSNUMMER,bredde,NVDB_BREDDE,hminhoeyrekant,NVDB_HMINHØYREKANT,hminmidt,NVDB_HMINMIDT,hminvenstrekant,NVDB_HMINVENSTREKANT,navn,NVDB_NAVN,skiltahoeyde,NVDB_SKILTAHØYDE,typehinder,NVDB_TYPEHINDERHØYDEBEGRENSNING,forbudretningskode,NVDB_FORBUDRETNINGSKODE
    -> AttributeFilter
AttributeFilter
    ATTR_NAME = OBJTYPE
    ATTR_VALUES = <BLANK>,<UNFILTERED>,Bruksklasse,Fartsgrense,Høydebegrensning,InnkjøringForbudt,Jernbanekryssing,Landbruksvegklasse,Svingerestriksjon,Vegsperring
    Bruksklasse -> bruksklasse (writer SPATIALITE_1)
    Fartsgrense -> fartsgrense (writer SPATIALITE_1)
    <UNFILTERED> -> AttributeFilter__UNFILTERED_
    Høydebegrensning -> hoeydebegrensning (writer SPATIALITE_1)
    InnkjøringForbudt -> innkjoeringforbudt (writer SPATIALITE_1)
    Landbruksvegklasse -> landbruksvegklasse (writer SPATIALITE_1)
    Vegsperring -> vegsperring (writer SPATIALITE_1)
    Jernbanekryssing -> jernbanekryssing (writer SPATIALITE_1)
AttributeFilter__UNFILTERED_: Inspector
    TACKATTRS = OBJTYPE
bruksklasse (writer SPATIALITE_1) [off]
    attributes: lrobjref_lokalid real(10,0), lrobjref_navnerom string(21), fraposisjon integer, tilposisjon integer, bruksklassehelaar string(15), bruksklassetele string(14), bruksklassevinter string(15), makstotalvektmodulvogntog real(5,2), makstotalvekttoemmertransport real(5,2), maksvogntoglengde integer, strekningsbeskrivelse string(73), strekningsbeskrivelsemodulvogntog string(42), veggruppe string(2)
fartsgrense (writer SPATIALITE_1) [off]
    attributes: lrobjref_lokalid real(10,0), lrobjref_navnerom string(21), fraposisjon integer, tilposisjon integer, arkivnummer real(11,0), fartsgrenseverdi integer, vedtaksnummer string(22)
hoeydebegrensning (writer SPATIALITE_1) [off]
    attributes: lrobjref_lokalid real(10,0), lrobjref_navnerom string(21), fraposisjon integer, tilposisjon integer, bredde real(5,2), hminhoeyrekant real(4,2), hminmidt real(4,2), hminvenstrekant real(4,2), navn string(12), skiltahoeyde real(3,1), typehinder string(14)
innkjoeringforbudt (writer SPATIALITE_1) [off]
    attributes: lrobjref_lokalid real(10,0), lrobjref_navnerom string(21), fraposisjon integer, tilposisjon integer, merknad string(19), skiltnummer integer, forbudretningskode integer
jernbanekryssing (writer SPATIALITE_1) [off]
    attributes: lrobjref_lokalid real(10,0), lrobjref_navnerom string(21), posisjon integer, typekryssing string(10)
landbruksvegklasse (writer SPATIALITE_1) [off]
    attributes: lrobjref_lokalid real(10,0), lrobjref_navnerom string(21), fraposisjon integer, tilposisjon integer, klasse string(15)
vegsperring (writer SPATIALITE_1) [off]
    attributes: lrobjref_lokalid real(10,0), lrobjref_navnerom string(21), posisjon integer, vegsperringtype string(10)

FME custom transformer Svingerestriksjonsgeometri
Beregner geometri med retning, for visualisering av svingerestriksjoner.

Svingerestriksjon (input)
    -> Counter
Counter
    SCOPE = Global
    START = 0
    DOMAIN = counter
    CNT_ATTR = _count
    -> StringConcatenator_3
StringConcatenator_3
    PARM_LINE = @Value(NVDB_SVINGEFORBUDFRAID.NAVNEROM)_@Value(NVDB_SVINGEFORBUDFRAID.LOKALID)
    VAL_ATTR = _fraident
    -> StringConcatenator_4
StringConcatenator_4
    PARM_LINE = @Value(NVDB_SVINGEFORBUDTILID.NAVNEROM)_@Value(NVDB_SVINGEFORBUDTILID.LOKALID)
    VAL_ATTR = _tilident
    -> FeatureMerger [input 1]
Veglenke (input)
    -> TopologyBuilder [input 2]
TopologyBuilder
    OVERLAPPING_MODE = No
    PROP_ATTRS = No
    ALL_EDGES = Yes
    CLEAN_DATA = Yes
    ALLOW_CYCLES = No
    MAX = 0
    LINE -> AttributeKeeper
AttributeKeeper
    KEEP_ATTRS = _ident,_arc_id,_from_node,_to_node
    -> GeometryExtractor
GeometryExtractor
    OGCVERSION = 1.1
    ATTR = _geometry
    GEOHASH_PRECISION_DISPLAY = ±9.3 mm (12 characters)
    OGEOSMS_URL_PREFIX = http://maps.google.com/?q=
    OMIT_NAMESPACES_DISPLAY = No
    LEVELS_ATTR = _levels
    KIND_LONG = FME Binary
    -> BulkAttributeRenamer
    -> AttributeCreator
AttributeCreator
    ATTR_LIST = _lenkerolle,Fra
    -> FeatureMerger [input 2]
Note: Kobler til "fra-lenke"
FeatureMerger
    PROCESS_DUPS = No
    MERGE_TYPE = Attributes Only
    JOIN_KEYS = @Value(_fraident) @Value(_ident)
    MERGED -> FeatureMerger_2 [input 1]
BulkAttributeRenamer
    REPLACE_STR = _to
    ATTRCHOICE = All Attributes
    PATTERN_ACTION_DISP = Add String Prefix
    -> AttributeCreator_2
AttributeCreator_2
    ATTR_LIST = _lenkerolle,Til
    -> FeatureMerger_2 [input 2]
Note: Kobler til "til-lenke"
FeatureMerger_2
    PROCESS_DUPS = No
    MERGE_TYPE = Attributes Only
    JOIN_KEYS = @Value(_tilident) @Value(_to_ident)
    MERGED -> GeometryReplacer
    MERGED -> GeometryReplacer_2
GeometryReplacer
    ATTR = _geometry
    KIND_LONG = FME Binary
    -> TestFilter_3
Note: Retning på "fra-lenke" / i forhold til noden
TestFilter_3
    TEST_LIST:
      BOOL_OP,OR,COMPOSITE_TEST,<Unused>,TEST_CLAUSE,"TEST @Value(_to_node) = @Value(_to_from_node)
      TEST @Value(_to_node) = @Value(_to_to_node)",_dirTo,BOOL_OP,OR,COMPOSITE_TEST,<Unused>,TEST_CLAUSE,"TEST @Value(_from_node) = @Value(_to_from_node)
      TEST @Value(_from_node) = @Value(_to_to_node)",_dirFrom
    DEFAULT_VALUE = <UNFILTERED>
    _dirFrom -> Orientor
    _dirTo -> TestFilter_2
Note: bytter retning
Orientor
    KIND = REVERSE
    ORIENTED -> TestFilter_2
TestFilter_2
    TEST_LIST = BOOL_OP,OR,COMPOSITE_TEST,<Unused>,TEST_CLAUSE,"TEST @Evaluate(@Length()) <= 30",Under30
    DEFAULT_VALUE = <UNFILTERED>
    <UNFILTERED> -> Snipper
    Under30 -> Aggregator
Note: Klipper
Snipper
    MEASUREMENTTYPE = 3D
    ENDLOCATIONATTR = @Length()
    STARTLOCATIONATTR = @Length()-30
    SNIPMODE = Distance (Value)
    -> Aggregator
GeometryReplacer_2
    ATTR = _to_geometry
    KIND_LONG = FME Binary
    -> TestFilter_4
Note: Retning på "til-lenke" / i forhold til noden
TestFilter_4
    TEST_LIST:
      BOOL_OP,OR,COMPOSITE_TEST,<Unused>,TEST_CLAUSE,"TEST @Value(_to_from_node) = @Value(_to_node)
      TEST @Value(_to_from_node) = @Value(_from_node)",_dirFrom,BOOL_OP,OR,COMPOSITE_TEST,<Unused>,TEST_CLAUSE,"TEST @Value(_to_to_node) = @Value(_to_node)
      TEST @Value(_to_to_node) = @Value(_from_node)",_dirTo
    DEFAULT_VALUE = <UNFILTERED>
    _dirTo -> Orientor_2
    _dirFrom -> TestFilter_5
Note: bytter retning
Orientor_2
    KIND = REVERSE
    ORIENTED -> TestFilter_5
TestFilter_5
    TEST_LIST = BOOL_OP,OR,COMPOSITE_TEST,<Unused>,TEST_CLAUSE,"TEST @Evaluate(@Length()) <= 30",Under30
    DEFAULT_VALUE = <UNFILTERED>
    <UNFILTERED> -> Snipper_2
    Under30 -> Aggregator
Note: Klipper
Snipper_2
    MEASUREMENTTYPE = 3D
    ENDLOCATIONATTR = 30
    STARTLOCATIONATTR = 0
    SNIPMODE = Distance (Value)
    -> Aggregator
Note: Slår sammen segmentene
Aggregator
    GROUP_BY = _count
    MODE = Assemble One Level
    ACCUM_ATTRS_NAME = Yes
    SEP = ,
    AGGREGATE_TYPE = Homogeneous Collection (If Possible)
    ORDERED = No
    AGGREGATE -> Utdata (output)
Utdata (output)

FME custom transformer SOSI_LRverdier_Heltall
Setter startverdi, sluttverdi og målt lengde for lenkene i henhold til SOSI Vegnett 4.5 og FKB-Vegnett 4.5:
    LRSTARTVERDI
    LRSLUTTVERDI
    LRMÅLTLENGDE
Dersom en eller flere av verdiene er angitt avledes de øvrige av denne eller disse, jf oppsettet under. Dersom målt lengde ikke er angitt (enten direkte eller indirekte) brukes geometrilengde, men avrunda til hele meter, ettersom lineære posisjoner i FKB-Vegnett er angitt i hele meter.
LRSTARTVERDI	LRSLUTTVERDI	LRMÅLTLENGDE	
			LRSTARTVERDI := 0, LRSLUTTVERDI := Round(@Length), LRMÅLTLENGDE := Round(@Length)
		X	LRSTARTVERDI := 0, LRSLUTTVERDI := LRMÅLTLENGDE
	X		LRSTARTVERDI := 0, LRMÅLTLENGDE := LRSLUTTVERDI 
	X	X	LRSTARTVERDI := LRSLUTTVERDI -  LRMÅLTLENGDE  
X			LRSLUTTVERDI  := LRSTARTVERDI + Round(@Length), LRMÅLTLENGDE :=  Round(@Length)
X		X	LRSLUTTVERDI  := LRSTARTVERDI + LRMÅLTLENGDE
X	X		LRMÅLTLENGDE := LRSLUTTVERDI - LRSTARTVERDI 
X	X	X	Ingen endring

INPUT (input)
    -> TestFilter
Note: Filtrering ut i fra om / LRSTARTVERDI, / LRSLUTTVERDI og / LRMÅLTLENGDE / er angitt
TestFilter
    TEST_LIST:
      BOOL_OP,AND,COMPOSITE_TEST,<Unused>,TEST_CLAUSE,"TEST LRSTARTVERDI ATTRIBUTE_IS_NULL <Unused>
      TEST LRSLUTTVERDI ATTRIBUTE_IS_NULL <Unused>
      TEST LRMÅLTLENGDE ATTRIBUTE_IS_NULL <Unused>",INGEN,BOOL_OP,AND,COMPOSITE_TEST,<Unused>,TEST_CLAUSE,"TEST LRSTARTVERDI ATTRIBUTE_IS_NULL <Unused>
      TEST LRSLUTTVERDI ATTRIBUTE_IS_NULL <Unused>
      TEST LRMÅLTLENGDE NOT_ATTRIBUTE_IS_NULL <Unused>",KUN_LENGDE,BOOL_OP,AND,COMPOSITE_TEST,<Unused>,TEST_CLAUSE,"TEST LRSTARTVERDI ATTRIBUTE_IS_NULL <Unused>
      TEST LRSLUTTVERDI NOT_ATTRIBUTE_IS_NULL <Unused>
      TEST LRMÅLTLENGDE ATTRIBUTE_IS_NULL <Unused>",KUN_SLUTT,BOOL_OP,AND,COMPOSITE_TEST,<Unused>,TEST_CLAUSE,"TEST LRSTARTVERDI ATTRIBUTE_IS_NULL <Unused>
      TEST LRSLUTTVERDI NOT_ATTRIBUTE_IS_NULL <Unused>
      TEST LRMÅLTLENGDE NOT_ATTRIBUTE_IS_NULL <Unused>",SLUTT_LENGDE,BOOL_OP,AND,COMPOSITE_TEST,<Unused>,TEST_CLAUSE,"TEST LRSTARTVERDI NOT_ATTRIBUTE_IS_NULL <Unused>
      TEST LRSLUTTVERDI ATTRIBUTE_IS_NULL <Unused>
      TEST LRMÅLTLENGDE ATTRIBUTE_IS_NULL <Unused>",KUN_START,BOOL_OP,AND,COMPOSITE_TEST,<Unused>,TEST_CLAUSE,"TEST LRSTARTVERDI NOT_ATTRIBUTE_IS_NULL <Unused>
      TEST LRSLUTTVERDI ATTRIBUTE_IS_NULL <Unused>
      TEST LRMÅLTLENGDE NOT_ATTRIBUTE_IS_NULL <Unused>",START_LENGDE,BOOL_OP,AND,COMPOSITE_TEST,<Unused>,TEST_CLAUSE,"TEST LRSTARTVERDI NOT_ATTRIBUTE_IS_NULL <Unused>
      TEST LRSLUTTVERDI NOT_ATTRIBUTE_IS_NULL <Unused>
      TEST LRMÅLTLENGDE ATTRIBUTE_IS_NULL <Unused>",START_SLUTT,BOOL_OP,AND,COMPOSITE_TEST,<Unused>,TEST_CLAUSE,"TEST LRSTARTVERDI NOT_ATTRIBUTE_IS_NULL <Unused>
      TEST LRSLUTTVERDI NOT_ATTRIBUTE_IS_NULL <Unused>
      TEST LRMÅLTLENGDE NOT_ATTRIBUTE_IS_NULL <Unused>",ALLE
    DEFAULT_VALUE = <UNFILTERED>
    INGEN -> AttributeCreator
    KUN_LENGDE -> AttributeCreator_2
    KUN_SLUTT -> AttributeCreator_3
    SLUTT_LENGDE -> AttributeCreator_4
    KUN_START -> AttributeCreator_5
    START_LENGDE -> AttributeCreator_6
    START_SLUTT -> AttributeCreator_7
    ALLE -> OUTPUT (output)
AttributeCreator
    ATTR_LIST = LRSTARTVERDI,0,LRSLUTTVERDI,@round(@Length()),LRMÅLTLENGDE,@round(@Length())
    -> OUTPUT (output)
AttributeCreator_2
    ATTR_LIST = LRSTARTVERDI,0,LRSLUTTVERDI,@Value(LRMÅLTLENGDE)
    -> OUTPUT (output)
AttributeCreator_3
    ATTR_LIST = LRSTARTVERDI,0,LRMÅLTLENGDE,@Value(LRSLUTTVERDI)
    -> OUTPUT (output)
AttributeCreator_4
    ATTR_LIST = LRSTARTVERDI,@Evaluate(@Value(LRSLUTTVERDI)-@Value(LRMÅLTLENGDE))
    -> OUTPUT (output)
AttributeCreator_5
    ATTR_LIST = LRSLUTTVERDI,@Value(LRSTARTVERDI)+@round(@Length()),LRMÅLTLENGDE,@Value(LRSTARTVERDI)+@round(@Length())
    -> OUTPUT (output)
AttributeCreator_6
    ATTR_LIST = LRSLUTTVERDI,@Value(LRSTARTVERDI)+@Value(LRMÅLTLENGDE)
    -> OUTPUT (output)
AttributeCreator_7
    ATTR_LIST = LRMÅLTLENGDE,@Value(LRSLUTTVERDI)+@Value(LRSTARTVERDI)
    -> OUTPUT (output)
OUTPUT (output)
